submodule rtbrick-igmp {
    yang-version 1.1;

    belongs-to rtbrick-config {
        prefix config;
    }

    import rtbrick-igmp-types {
        prefix "rtb-igmp-types";
    }

    import rtbrick-types {
        prefix "rtb-types";
    }

    organization
        "Rtbrick";

    contact
      "yang-support@rtbrick.com";

    description
        "This module contains the YANG model for the IGMP protocol configuration

        +-> multicast-options
        | +-> igmp
        |   +-> interface-profile
        |     +-> default-filter-action
        |     +-> immediate-leave
        |     +-> querier-timeout-interval
        |     +-> query-interval
        |     +-> query-max-response-time
        |     +-> start-query-count
        |     +-> start-query-interval
        |     +-> policy
        |
        +-> instance
          +-> robustness
          +-> source-address
          +-> interfaces
          | +-> interface
          |   +-> version
          |   +-> max-groups
          |   +->interface-profile
          +-> static-group";

    revision 2020-09-09 {
        description "First revision of IGMP configuration";
        reference "None";
    }

    grouping interface-config-profile {
        description "The interface configuration profile";
        list interface-profile {
            key "profile-name";
            description "IGMP interface configuration profile";
            reference
                '{
                    "table-getter": {
                        "table-name": "global.igmp.interface.profile.config",
                        "type" :  "igmp_interface_profile_config_table"
                    }
                }';
            leaf profile-name {
                type string {
                    length "1..64";
                }
                description "IGMP interface config profile name";
                reference
                    '{
                        "attribute-getter" : {
                            "attribute" : "config_profile_name"
                        }
                    }';
            } //leaf default-filter-action
            leaf immediate-leave {
                type rtb-types:enable-disable-type;
                description "If enabled, IGMP perform an immediate leave upon
                    receiving an IGMP group leave message.
                    If the router is IGMP-enabled, it sends an
                    IGMP last member query with a last member query
                    response time. However, the router does not wait for
                    the response time before it prunes off the group";
                reference
                    '{
                        "attribute-getter" : {
                            "attribute" : "immediate_leave"
                        }
                    }';
            } //leaf immediate-leave
            leaf querier-timeout-interval {
                type uint32 {
                    range "1..1024";
                }
                units "seconds";
                description "IGMP other querier timeout. Default: 425s";
                reference
                    '{
                        "attribute-getter" : {
                            "attribute" : "querier_timeout"
                        }
                    }';
            }//leaf querier-timeout-interval
            leaf query-interval {
                type uint32 {
                    range "1..1024";
                }
                units "seconds";
                description "The query interval is the interval between general
                    queries sent by the Querier. Default: 125s";
                reference
                    '{
                        "attribute-getter" : {
                            "attribute" : "query_interval"
                        }
                    }';
            }//leaf query-interval
            leaf query-max-response-time {
                type uint32 {
                    range "1..1024";
                }
                units "seconds";
                description "Query maximum response time specifies the maximum time
                    allowed before sending a responding report. Default: 100s";
                reference
                    '{
                        "attribute-getter" : {
                            "attribute" : "maximum_query_response_time"
                        }
                    }';
            }//leaf query-max-response-time
            leaf start-query-count {
                type uint32 {
                    range "1..1024";
                }
                description "Number of general query sent upon IGMP startup. Default: 3";
                reference
                    '{
                        "attribute-getter" : {
                            "attribute" : "start_query_count"
                        }
                    }';
            }//leaf start-query-count
            leaf start-query-interval {
                type uint32 {
                    range "1..1024";
                }
                units "seconds";
                description "The interval at which general query sent upon IGMP
                    startup. Default: 31s";
                reference
                    '{
                        "attribute-getter" : {
                            "attribute" : "start_query_interval"
                        }
                    }';
            }//leaf start-query-interval
            leaf filter-policy {
                type string {
                    length "1..64";
                }
                description "IGMP membership filtering policy name";
                reference
                    '{
                        "attribute-getter" : {
                            "attribute" : "filter_policy_name",
                            "expansion-getter" : {
                                "package":"igmp",
                                "method" : "igmp_policy_name_expander"
                            }
                        }
                    }';
            }//leaf filter-policy
            leaf ssm-map-policy {
                type string {
                    length "1..64";
                }
                description "IGMP SSM policy name. The policy for (*,G) mapping to (S,G)";
                reference
                    '{
                        "attribute-getter" : {
                            "attribute" : "ssm_policy_name",
                            "expansion-getter" : {
                                "package":"igmp",
                                "method" : "igmp_policy_name_expander"
                            }
                        }
                    }';
            }//leaf ssm-map-policy
        }//list interface-profile
    }

    grouping igmp-multicast-options {
        description "The policy for (*,G) mapping to (S,G)";
        container igmp {
            description "The policy for (*,G) mapping to (S,G)";
            uses interface-config-profile;
        }//container igmp
    } //grouping igmp

    grouping interface-config-attributes-igmp {
        description "Per interface configuration for IGMP";
        leaf version {
            type rtb-igmp-types:igmp-version;
            description "IGMP version. Default: IGMPv3";
            reference
                '{
                    "attribute-getter" : {
                        "attribute" : "version"
                    }
                }';
        }//leaf version
        leaf max-groups {
            type uint32 {
                range "1..10000";
            }
            description "The maximum number of groups that IGMP can join.
                Default: 8192";
            reference
                '{
                    "attribute-getter" : {
                        "attribute" : "max_members_per_interface"
                    }
                }';
        }//leaf max-groups
        leaf interface-profile {
            type string {
                length "1..64";
            }
            description "IGMP interface configuration profile name";
            reference
                '{
                    "attribute-getter" : {
                        "attribute" : "config_profile_name",
                        "expansion-getter" : {
                            "package":"igmp",
                            "method" : "igmp_interface_profile_name_expander"
                        }
                    }
                }';
        }//uses interface-profile;
    }//grouping interface-config-attributes-igmp

    grouping igmp-multicast-options-top {
        description
        "Top-level grouping containing a list of multicast options";
        container multicast-options {
        description
        "Container for list of multicast options";
            uses igmp-multicast-options;
        }
    }

    grouping igmp-top {
        description "This grouping define top-level IGMP model data";
        container igmp {
            presence igmp;
            description "Protocol IGMP configuration";
            reference
                '{
                    "table-getter": {
                        "table-name": "global.igmp.instance.config",
                        "type" :  "igmp_instance_config_table",
                        "inherit-attribute":["instance_name"]
                    }
                }';

            leaf robustness-variable {
                type uint8 {
                    range "0..255";
                }
                description "Protocol robustness. Default: 3";
                reference
                    '{
                        "attribute-getter" : {
                            "attribute" : "robustness"
                        }
                    }';
            }//leaf robustness-variable

            leaf source-address {
                //type inet:ipv4-address;
                type rtb-igmp-types:ipv4-multicast-source-address;
                description "Source address for the IGMP Packets. Default: 0.0.0.0";
                reference
                    '{
                        "attribute-getter" : {
                            "attribute" : "source4"
                        }
                    }';
            }//leaf source-address

            container interfaces {
                description "Protocol IGMP configuration";
                list interface {
                    key "interface-name";
                    description "List of IGMP interfaces.*-";
                    reference
                        '{
                            "table-getter": {
                                "library": "libigmp-cmd.so",
                                "symbol": "igmp_yang_config_interface_table_templ",
                                "type" :  "igmp_interface_config_table"
                            }
                        }';
                    leaf interface-name {
                        type string {
                            length "1..64";
                        }
                        description "Reference to an entry in the global interface list";
                        reference
                            '{
                                "attribute-getter" : {
                                    "attribute" : "interface_name",
                                    "expansion-getter" : {
                                        "package":"igmp",
                                        "method" : "igmp_logical_interface_name_expander"
                                    }
                                }
                            }';
                    }//leaf interface-name
                    uses interface-config-attributes-igmp;
                }//list interfaces
            }//container interface

            list static-group {
                key "group-address source-address outgoing-interface";
                description "A static multicast route, (*,G) or (S,G)";
                reference
                    '{
                        "table-getter": {
                            "library": "libigmp-cmd.so",
                            "symbol": "igmp_yang_config_static_join_table_templ",
                            "type" :  "igmp_static_membership_config_table"
                        }
                    }';
                leaf group-address {
                    type rtb-igmp-types:ipv4-multicast-group-address;
                    description  "Multicast group IP address";
                    reference
                        '{
                            "attribute-getter" : {
                                "attribute" : "group4"
                            }
                        }';
                }//leaf group-address
                leaf source-address {
                    type rtb-igmp-types:ipv4-multicast-source-address;
                    description  "Multicast source IP address";
                    reference
                        '{
                            "attribute-getter" : {
                                "attribute" : "source4"
                            }
                        }';
                }//leaf source-address
                leaf outgoing-interface {
                    type string {
                        length "1..64";
                    }
                    description  "Multicast outbound interface name";
                    reference
                        '{
                            "attribute-getter" : {
                                "attribute" : "oif",
                                "expansion-getter" : {
                                    "package":"igmp",
                                    "method" : "igmp_static_group_interface_name_expander"
                                }
                            }
                        }';
                }//leaf outgoing-interface
            }//list static-group
        }//container igmp
    }//grouping igmp-top
}
