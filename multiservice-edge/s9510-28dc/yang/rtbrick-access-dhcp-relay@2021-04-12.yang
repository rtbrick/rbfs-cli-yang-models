submodule rtbrick-access-dhcp-relay {

    yang-version 1.1;

    belongs-to rtbrick-config {
        prefix config;
    }

    import rtbrick-types {
        prefix "rtb-types";
    }

    organization
      "RtBrick";
    contact
      "yang-support@rtbrick.com";
    description
      "This sub-module defines the YANG structure for the access DHCP relay configurations";
    revision 2021-04-12 {
        description "First revision";
        reference "None";
    }

    grouping access-dhcp-relay {
        description "Global access DHCP relay configuration";

        list dhcp-relay {
            key "interface";
            description "Global DHCP relay configuration";
            reference
            '{
                "table-getter": {
                    "table-name": "global.access.dhcp.relay.config",
                    "type": "dhcp_relay_config_table"
                }
            }';
            leaf interface {
                type rtb-types:logical-interface-type;
                description "Logical interface expecting DHCP client packets";
                reference
                '{
                    "attribute-getter": {
                        "attribute": "ifl_name",
                        "expansion-getter": {
                            "package": "subsMgmt",
                            "method": "access_physical_ifl_name_expander"
                        }
                    }
                }';
            }
            leaf-list dhcp-server {
                type string {
                    length "1..64";
                }
                description "DHCP server";
                must '/access/dhcp-server[server-name = current()]' {
                    error-message "DHCP relay server does not exist";
                }
                reference
                '{
                    "attribute-getter": {
                        "attribute": "dhcp_server_list",
                        "expansion-getter": {
                            "package": "subsMgmt",
                            "method": "access_dhcp_server_name_expander"
                        }
                    }
                }';
            }
            leaf proxy-mode {
                type rtb-types:boolean-type;
                description "Enable relay proxy mode";
                reference
                '{
                    "attribute-getter": {
                        "attribute": "proxy_mode"
                    }
                }';
            }
            leaf agent-circuit-id {
                type string {
                    length "1 .. 63";
                }
                description "Add Agent-Circuit-Id (option 82)";
                reference
                '{
                    "attribute-getter": {
                        "attribute": "agent_circuit_id"
                    }
                }';
            }
            leaf agent-remote-id {
                type string {
                    length "1 .. 63";
                }
                description "Add Agent-Remote-ID (option 82)";
                reference
                '{
                    "attribute-getter": {
                        "attribute": "agent_remote_id"
                    }
                }';
            }
            leaf dhcp-min-elapsed-time {
                type uint16 {
                    range "1..600";
                }
                description "DHCP minimum elapsed time in seconds";
                reference
                '{
                    "attribute-getter": {
                        "attribute": "dhcp_min_elapsed_sec"
                    }
                }';
            }
        }
    }
}
