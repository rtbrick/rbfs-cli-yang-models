submodule rtbrick-traffic-sampling {
  yang-version 1.1;

  belongs-to rtbrick-config {
    prefix config;
  }

  import rtbrick-types {
    prefix types;
  }

  import ietf-inet-types {
    prefix inet;
  }

  organization
    "Rtbrick";

  contact
    "Author : Jashmikant Mohanty (jashmikant@rtbrick.com)";

  description
    "This module describes the YANG model for the traffic sampling configuration.";

  revision 2024-07-20 {
    description
      "Configuration hierarchy for access control list";

    reference
      "None";
  }

  typedef type-traffic-sampling {
    type enumeration {
      enum "sflow" {
        value 1;
        description
          "SFlow sampling protocol";
      }
    }
    description
      "traffic sampling export protocol data type";
  }

  typedef type-direction {
    type enumeration {
      enum "ingress" {
        value 1;
        description
          "Ingress";
      }
      enum "egress" {
        value 2;
        description
          "Egress";
      }
      enum "both" {
        value 3;
        description
          "both";
      }
    }
    description
      "direction data type";
  }

  grouping traffic-sampling-top {
    description
      "Top-level grouping containing a list of traffic sampling config.";
    container traffic-sampling {
	    presence traffic-sampling;
      description
        "container for traffic-sampling";
      list collector {
        description
          "collector-list";
        key "collector-id";
        reference
          '{
               "table-getter": {
                   "table-name" : "global.traffic.sampling.collector.config",
                   "type"    : "global_traffic_sampling_collector_config",
                   "default-attribute" : [ { "num_of_samples" : "1" } ]
               }
           }';
        leaf collector-id {
          description
            "Collector identifier";
          type int8 {
            range "1 .. 4";
          }
          reference
            '{
                 "attribute-getter" : {
                     "attribute" : "collector_id"
                 }
             }';
        }
        leaf instance {
          description
            "Name of the instance from which collector address is reachable";
          type types:string64;
          reference
            '{
                 "attribute-getter" : {
                     "attribute" : "instance_name",
                     "expansion-getter" : {
                         "package":"fwdinfra",
                         "method" :"fwd_infra_instance_expansion"
                     }
                 }
             }';
        }
        leaf export-protocol {
          description
            "Traffic sampling protocol";
          type type-traffic-sampling;
          reference
            '{
                 "attribute-getter" : {
                     "attribute" : "export_protocol"
                 }
             }';
        }
        container address {
	        presence address;
          description
            "Collector address";
          reference
            '{
                 "table-getter": {
                     "table-name" : "global.traffic.sampling.collector.config",
                     "type"    : "global_traffic_sampling_collector_config",
                     "inherit-attribute" : [ "collector_id" ]
                 }
             }';

          leaf ipv4 {
            description
              "Collector IPv4 address";
            type inet:ipv4-address-no-zone;
            reference
              '{
                   "attribute-getter" : {
                       "attribute" : "collector_ipv4_address"
                   }
               }';
          }
        }

        leaf sampling-rate {
          description
            "Sampling rate(1/sampling-rate)";
          type int32 {
            range "100..50000";
          }
          reference
            '{
                 "attribute-getter" : {
                     "attribute" : "sampling_rate"
                 }
             }';
        }

        leaf description {
          description
            "Description of collector";
          type types:string64;
          reference
            '{
                 "attribute-getter" : {
                     "attribute" : "description"
                 }
             }';
        }
        leaf destination-udp-port {
          description
            "UDP port for the collector destination";
          type int32 {
            range "1 .. 65535";
          }
          reference
            '{
                 "attribute-getter" : {
                     "attribute" : "udp_dest_port"
                 }
             }';
        }
        leaf agent-id {
          description
            "sFlow agent-id";
          must 'count(../../collector[agent-id = current()]) = count(../../collector/agent-id)' {
            error-message "Agent-Id should be unique for the device.";
          }
          type inet:ipv4-address-no-zone;
          reference
            '{
                 "attribute-getter" : {
                     "attribute" : "agent_id"
                 }
             }';
        }
      }
      list profile {
        description
          "profile name";
        key "profile-name";
        reference
          '{
               "table-getter": {
                   "table-name" : "global.traffic.sampling.profile.config",
                   "type"    : "traffic_sampling_config_profile"
               }
           }';
        leaf profile-name {
          description
            "Profile name for traffic sampling";
          type types:string64;
          reference
            '{
                 "attribute-getter" : {
                     "attribute" : "profile_name"
                 }
             }';
        }
        leaf collector {
          description
            "collector id used by the profile";
          type int8 {
            range "1 .. 4";
          }
          reference
            '{
                 "attribute-getter" : {
                     "attribute" : "collector_id"
                 }
             }';
        }
        leaf description {
          description
            "Description of profile";
          type types:string64;
          reference
            '{
                 "attribute-getter" : {
                     "attribute" : "description"
                 }
             }';
        }
        leaf direction {
          description
            "Direction of traffic to be sampled";
          type type-direction;
          reference
            '{
                 "attribute-getter" : {
                     "attribute" : "direction"
                 }
             }';
        }
      }
    } // container traffic sampling
  } // grouping traffic-sampling-top
}
