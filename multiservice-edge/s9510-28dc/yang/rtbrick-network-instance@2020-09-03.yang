submodule rtbrick-network-instance {
    yang-version 1.1;

    belongs-to rtbrick-config {
        prefix config;
    }

    import ietf-inet-types {
        prefix "inet";
    }
    import rtbrick-types {
       prefix types;
    }

    include rtbrick-isis;
    include rtbrick-bgp;
    include rtbrick-validation;
    include rtbrick-bfd;
    include rtbrick-ospf;
    include rtbrick-static;
    include rtbrick-igmp;
    include rtbrick-pim;
    include rtbrick-ldp;
    include rtbrick-lwip;
    include rtbrick-snmp;

    organization
      "Rtbrick";
    contact
      "Author : Navaneeth Y V (navaneethyv@rtbrick.com)
              : Kuldeep Mishra (kuldeep@rtbrick.com)";
    description
      "This is the instance related configuration YANG file";

    revision 2020-09-03 {
        description
        "Included rtbrick-static submodule";

        reference "None";
    }

    revision 2020-06-20 {
        description
        "Initial instance configuration hierarchy, other modules are to be added as uses in this hierarchy as needed,
    Derived from openconfig-network-instance.yang of openconfig";

        reference "None";
    }


    grouping af-policy {
        description "Instance address family Policy related configuration";
        container policy {
	    when '../afi != "l2vpn"';
            description "Instance address family Policy related configuration";
            reference
            '{
                "table-getter": {
                    "table-name": "global.instance.afi-safi.config",
                    "type" :  "instance_af_config_table",
                    "inherit-attribute":["instance_name", "afi", "safi"]
                }
            }';
            leaf-list import {
                type types:policy-name-type;
                must "count(../import) <= 10"{
                    error-message "Maximum of 10 polices are supported in a policy chain";
                }
                ordered-by user;
                description "Import policy name (max 64 characters)";
                reference
                '{
                    "attribute-getter" : {
                        "attribute" : "import_route_map"
                    }
                }';
            }
            leaf-list export {
                type types:policy-name-type;
                must "count(../export) <= 10"{
                    error-message "Maximum of 10 polices are supported in a policy chain";
                }
                ordered-by user;
                description "Export policy name (max 64 characters)";
                reference
                '{
                    "attribute-getter" : {
                        "attribute" : "export_route_map"
                    }
                }';
            }
        }
    }

    grouping route-target {
        description "Route target related configuration";
        container route-target {
            description "Route target related configuration";
            reference
            '{
                "table-getter": {
                    "table-name": "global.instance.afi-safi.config",
                    "type" :  "instance_af_config_table",
                    "inherit-attribute":["instance_name", "afi", "safi"]
                }
            }';
            leaf-list import {

                type types:route-target-type;
                description "VPN Route Target. Format: target:{as_number | ipv4_address}:rt_identifier";
                reference
                '{
                    "attribute-getter" : {
                        "attribute" : "import_rt"
                    }
                }';
            }
            leaf-list export {
                type types:route-target-type;
                description "VPN Route Target. Format: target:{as_number | ipv4_address}:rt_identifier";
                reference
                '{
                    "attribute-getter" : {
                        "attribute" : "export_rt"
                    }
                }';
            }
        }
    }

    grouping import-rib {
        list import-rib {
            description "Route import related configuration";
            key "instance";
            reference
                '{
                    "table-getter": {
                        "table-name": "global.instance.afi-safi.import-rib.config",
                        "type" : "instance_af_import_rib_config_table",
                        "inherit-attribute": ["instance_name", "afi", "safi"]
                    }
                }';

            leaf instance {
                type types:string64;
                description "Name of the source instance from which routes are imported";
                reference
                    '{
                        "attribute-getter" : {
                            "attribute" : "src_instance"
                        }
                    }';
               must '(. != ../../../name)' {
                    error-message "Routes cannot be imported from the self instance";
                }

            }

            leaf policy {
                type types:string64;
                description "Name of the policy applicable on the imported routes";
                reference
                    '{
                        "attribute-getter" : {
                            "attribute" : "policy_name"
                        }
                    }';
            }

            must '((../afi = "ipv4") or (../afi = "ipv6"))' {
                error-message "Import-rib feature supported only for ipv4 and ipv6 address-family";
            }
            must '(../safi = "unicast")' {
                error-message "Import-rib feature supported only for unicast safi";
            }

        }
    }


    grouping address-family {
        description "Instance address family related configurations";
        list address-family {
            key "afi safi";
            description "Instance address family related configurations";
            reference
            '{
                "table-getter": {
                    "type" :  "instance_af_config_table",
                    "table-name": "global.instance.afi-safi.config",
                    "inherit-attribute":["instance_name"]
                }
            }';
            leaf afi {
                type types:afi;
                description "Address family indicator";
                reference
                '{
                    "attribute-getter" : {
                        "attribute" : "afi"
                    }
                }';
            }
            leaf safi {
                must '(../afi != "l2vpn" and . != "evpn" and . != "evpn-vpws" and .
                != "vpls-vpws" and . != "vpls") or (../afi = "l2vpn" and
                (. = "evpn" or . = "evpn-vpws" or . = "vpls-vpws" or . = "vpls"))' {
                    error-message "l2vpn afi can only be configured with
                    evpn/evpn-vpws/vpls-vpws safi and vice-versa";
                }
                type types:safi;
                description "Subsequent address family indicator";
                reference
                '{
                    "attribute-getter" : {
                        "attribute" : "safi"
                    }
                }';
            }
            uses af-policy;
            uses route-target;
            uses import-rib;
        }
    }

    grouping network-instance-top {
        description
        "Top-level grouping containing a list of network instances.";
        list instance {
            key "name";
            description
                    "Network instance configuration";
            reference
            '{
                "table-getter": {
                    "table-name" : "global.instance.config",
                    "type"    :  "instance_config_table"
                }
            }';
            leaf name {
                type types:string64;
                description
                    "An operator-assigned unique name for the network instance";
                reference
                '{
                    "attribute-getter" : {
                        "attribute" : "instance_name"
                    }
                 }';
            }
            leaf ipv4-router-id {
                type inet:ipv4-address;
                description "IPv4 router id of the routing instance";
                reference
                '{
                    "attribute-getter" : {
                        "attribute" : "router_id4"
                    }
                }';
            }
            leaf route-distinguisher {
                type types:route-distinguisher-type;
                description "VPN Route Distinguisher. Format: {as_number | ipv4_address}:rd_identifier";
                reference
                '{
                    "attribute-getter" : {
                        "attribute" : "rd"
                    }
                }';
            }
            leaf address-translation {
                type types:boolean-true;
                description "Enable address-translation on this instance";
                reference
                '{
                    "attribute-getter" : {
                        "attribute" : "nat_enabled"
                    }
                }';
            }

            uses address-family;
            uses tcp-config;

            container protocol {
            description
                "Protocol configuration";
                uses isis-top;
                uses bgp-top;
                uses validation-top;
                uses ldp-top;
                uses ospf-top;
                uses pim-top;
                uses igmp-top;
                uses bfd-top;
                uses snmp-top;
            }
            uses static-top;
        }
    }

    uses network-instance-top;
}
