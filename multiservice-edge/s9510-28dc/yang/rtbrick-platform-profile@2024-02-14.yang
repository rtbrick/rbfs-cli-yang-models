submodule rtbrick-platform-profile {

    yang-version 1.1;

    belongs-to rtbrick-config {
        prefix config;
    }

    organization
        "RtBrick";

    contact
      "yang-support@rtbrick.com";

    description
        "This sub-module contains yang structure for platform profile";

    revision 2024-02-14 {
        description "First revision";
        reference "None";
    }

    typedef profile-name {
        type enumeration {
            enum nat_4q {
                value "1";
                description "NAT 4Q";
            }
            enum nat_1q {
                value "2";
                description "NAT 1Q";
            }
            enum 1q {
                value "3";
                description "1Q";
            }
        }
        description "Platform Profiles";
    }

    typedef ipoe-mode-type {
        type enumeration  {
            enum  standby-forwarding {
                value "1";
                description "Active-Active mode";
            }
            enum  standby-non-forwarding {
                value "2";
                description "Active-Standby mode";
            }
        }
    }

    grouping platform-profile-config {
        description
            "Grouping for platform-profile model";

        container platform {
	        presence platform;
            description
                "Top-level container for platform-profile data";

            list profile {
                reference
                '{
                    "table-getter": {
                        "table-name" : "global.platform.profile.config",
                        "type"    : "platform_profile_table"
                    }
                }';
                description "Platform profile";
                key "profile_name";
                must 'count(../profile) <= 1' {
                    error-message "due to platform profile conflict. Only one system platform profile is allowed at a time.";
                }
                leaf profile_name {
                description "Platform profile";
                type string {
                    length "1 .. 64";
                }
                reference
                    '{
                        "attribute-getter" : {
                            "attribute" : "profile_name",
                            "expansion-getter" : {
                                "package":"fwdinfra",
                                "method" :"fwd_infra_platform_profile_expander"
                            }
                        }
                    }';
                }
            leaf-list feature {
                description "Platform feature";
                type string {
                    length "1 .. 64";
                }
                reference
                    '{
                        "attribute-getter" : {
                            "attribute" : "feature_name",
                            "expansion-getter" : {
                                "package":"fwdinfra",
                                "method" :"fwd_infra_platform_feature_expander"
                            }
                        }
                    }';
            }

            leaf ipoe-mode {
                description "High availability ipoe operation mode";
                type ipoe-mode-type;
                reference
                    '{
                        "attribute-getter" : {
                            "attribute" : "ipoe_mode"
                        }
                    }';

            }
            }
        }
    }

    grouping platform-profile-top {
        description
            "Top-level grouping for platform-profile model";

        uses platform-profile-config;
    }
}
