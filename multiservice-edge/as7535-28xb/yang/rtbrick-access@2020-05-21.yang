submodule rtbrick-access {

    yang-version 1.1;

    belongs-to rtbrick-config {
       prefix config;
    }

    include rtbrick-access-aaa-profile;
    include rtbrick-access-aaa-radius-profile;
    include rtbrick-access-aaa-radius-server;
    include rtbrick-access-access-profile;
    include rtbrick-access-interface-profile;
    include rtbrick-access-l2tp-pool;
    include rtbrick-access-l2tp-profile;
    include rtbrick-access-pool;
    include rtbrick-access-service-profile;
    include rtbrick-access-user-profile;
    include rtbrick-access-dhcp-relay;
    include rtbrick-access-dhcp-server;
    include rtbrick-access-dhcpv6-server;

    organization
      "RtBrick";
    contact
      "yang-support@rtbrick.com";
    description
      "This sub-module defines the YANG structure for the access module.";
    revision 2020-05-21 {
        description "First revision";
        reference "None";
    }

    grouping access-top {

      container access {
          description "Global access configuration";
          reference
          '{
              "table-getter": {
                  "table-name": "global.access.config",
                  "type": "access_global_config_table",
                  "default-attribute" : [ { "mode": "global" } ]
              }
          }';
          leaf chassis-id {
              type uint8 {
                range "0..15";
              }
              description "Chassis ID for this node";
              reference
              '{
                  "attribute-getter": {
                      "attribute": "chassis_id"
                  }
              }';
          }
          leaf chassis-subscriber-limit {
              type uint32;
              description "Chassis subscriber limit for this node";
              reference
              '{
                  "attribute-getter": {
                      "attribute": "chassis_subscriber_limit"
                  }
              }';
          }
          leaf terminate-history-timeout {
              type uint16 {
                range "0..720";
              }
              description "Terminate history timeout in hours";
              reference
              '{
                  "attribute-getter": {
                      "attribute": "terminate_history_timeout"
                  }
              }';
          }
          uses access-aaa-profile;
          uses access-aaa-radius-profile;
          uses access-aaa-radius-server;
          uses access-access-profile;
          uses access-interface-profile;
          uses access-l2tp-pool;
          uses access-l2tp-profile;
          uses access-pool;
          uses access-user-profile;
          uses access-service-profile;
          uses access-dhcp-relay;
          uses access-dhcp-server;
          uses access-dhcpv6-server;
      }
    }

    uses access-top;
}
