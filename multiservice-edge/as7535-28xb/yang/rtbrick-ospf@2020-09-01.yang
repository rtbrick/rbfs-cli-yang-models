submodule rtbrick-ospf {
    yang-version 1.1;
    belongs-to rtbrick-config {
        prefix config;
    }

    organization
      "Rtbrick";
    contact
      "yang-support@rtbrick.com";

    description
        "This sub module contains the top level configurations of dummy ospf configuration to help rtbrick roles
  	This must be dated before the latest package";

    revision 2020-09-01 {
        description
          "Dummy ospf yang file";
        reference "None";
    }

    grouping ospf-instance_id_ipv6 {
        description "Dummy OSPF ipv6 address family type grouping";
        container instance-id {
            description
              "Dummy OSPF ipv6 instance configuration";
            reference
              "None";
            uses ospf-segment-routing-v3;
            uses ospf-area-v3;
        }
    }

    grouping ospf-segment-routing-v3 {
        description
          "Dummy OSPF Segment routing grouping";
        container segment-routing {
            container srgb {
                description "Dummy OSPF ipv6 srgb configuration";
                reference
                  "None";
                leaf base {
                    type uint32;
                    description
                        "Dummy Base label for srgb block";
                    reference
                      "None";
                }
                leaf range {
                    type uint32;
                    description
                        "Dummy label range for srgb block";
                    reference
                      "None";
                }
            }
        }
    }

    grouping ospf-area-v3 {
        description
            "Dummy OSPF ipv6 area configs grouping";
        container area {
                description
                  "Dummy OSPF ipv4 srgb configuration";
                reference
                  "None";
            uses ospf-interface-v3;
        }
    }

    grouping ospf-interface-v3 {
        description
            "Dummy OSPF interface related configuration grouping";
        container interface {
                description
                  "Dummy OSPF ipv6 interface configuration";
                reference
                  "None";

            uses ospf-interface-segment-routing-v3;
        }
    }

    grouping ospf-interface-segment-routing-v3 {
        description "Dummy OSPF segment-routing grouping";
        container segment-routing {
            description
              "Dummy Segment routing configuration";
            reference
              "None";
            leaf index {
                type uint32;
                description
                  "Dummy OSPF interface segment index";
                reference
                  "None";
            }
        }
    }

    grouping ospf-address-family_ipv6 {
        description
          "Dummy OSPF ipv6 address family type grouping";
        container ipv6 {
            uses ospf-instance_id_ipv6;
        }
    }

    grouping ospf-segment-routing {
        description
          "Dummy OSPF Segment routing grouping";
        container segment-routing {
            container srgb {
                description
                  "Dummy OSPF ipv4 srgb configuration";
                reference
                  "None";
                leaf base {
                    type uint32;
                    description
                        "Dummy Base label for srgb block";
                    reference
                      "None";
                }
                leaf range {
                    type uint32;
                    description
                        "Dummy label range for srgb block";
                    reference
                      "None";
                }
            }
        }
    }

    grouping ospf-area {
        description
            "Dummy OSPF area related configuration grouping";
        container area {
            description
              "Dummy OSPF ipv4 area configuration";
            reference
              "None";
            uses ospf-interface;
        }
    }

    grouping ospf-interface {
        description
            "Dummy OSPF interface related configuration grouping";
        container interface {
            description "Dummy OSPF interface configuration";
            reference
              "None";
            uses ospf-interface-segment-routing;
        }
    }

    grouping ospf-interface-segment-routing {
        description "Dummy OSPF segment-routing grouping";
        container segment-routing {
            description "Dummy Segment routing configuration";
            reference
              "None";
            leaf index {
                type uint32;
                description
                    "Dummy OSPF interface segment index";
                reference
                  "None";
            }
        }
    }

    grouping ospf-address-family_ipv4 {
        description
          "Dummy OSPF ipv4 address family type grouping";
        container ipv4 {
            uses ospf-segment-routing;
            uses ospf-area;
        }
    }

    grouping ospf-address-family {
        description
          "Dummy OSPF Family types";
        container address-family {
            uses ospf-address-family_ipv4;
            uses ospf-address-family_ipv6;
        }
    }

    grouping ospf-top {
        description "Dummy OSPF top level config";
        container ospf {
            status obsolete;
            description
              "Dummy OSPF protocol configuration";
            uses ospf-address-family;
        }
    }
}
