submodule rtbrick-access-dhcp-relay {
    yang-version 1.1;
    belongs-to rtbrick-config {
        prefix config;
    }

    organization
      "Rtbrick";
    contact
      "yang-support@rtbrick.com";

    description
        "This sub module contains the top level configurations of dummy access-dhcp-relay config to help rtbrick roles.
  	This must be pre-date the older package";

    revision 2020-01-01 {
        description
          "Dummy access-dhcp-relay file";
    }

    grouping access-dhcp-relay {
        description "Dummy global access-dhcp-relay top level config";
    }
}
