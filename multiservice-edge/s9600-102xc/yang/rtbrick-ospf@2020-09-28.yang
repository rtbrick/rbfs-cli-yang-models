submodule rtbrick-ospf {
    yang-version 1.1;
    belongs-to rtbrick-config {
        prefix config;
    }

    import ietf-inet-types {
        prefix "inet";
    }
    import rtbrick-types {
        prefix "rtb-types";
    }
    import rtbrick-ospf-types {
        prefix "rtb-ospf-types";
    }

    organization "RtBrick";

    contact
      "yang-support@rtbrick.com";

    description
        "This module describes a YANG model for OSPF configuration.

    This model supports the following OSPF configuration level
    hierarchy:

      OSPF
        |
        +-> [ Global OSPF configuration ]
          +-> Area
            +-> Interface";

    revision "2020-09-28" {
      description
        "First revision of OSPF configuration";
      reference
        "None";

    }

    typedef ospf-network-type {
        type enumeration {
            enum broadcast {
                value "1";
                description "Network type broadcast";
            }
            enum p2p {
                value "2";
                description "Network type P2P";
            }
        }
        description "OSPF network types";
    }

    typedef ospf-area-type {
        type enumeration {
            enum stub {
                value "3";
                description "Area type stub";
            }
            enum totally-stub {
                value "5";
                description "Area type totally-stub";
            }
        }
        description "OSPF network types";
    }

    typedef ospf-afi {
        type enumeration {
            enum ipv4 {
                value "0";
                description "IPv4 address";
            }
            enum ipv6 {
                value "1";
                description "IPv6 address";
            }
        }
        description "Afi data type";
    }

    grouping ospf-interface-segment-routing-v3 {
        description "OSPF segment-routing grouping";
        container segment-routing {
            description "Segment routing configuration";
            reference
            '{
                "table-getter": {
                    "library": "libospfyang.so",
                    "symbol":  "ospf_get_interface_v3_tbl_templ",
                    "type" :   "ospf_interface_config",
                    "default-attribute": [{"afi": "ipv6"}],
                    "inherit-attribute":["instance_name", "area_id", "interface"]
                }
            }';
            leaf index {
                type uint32;
                must "../../../../segment-routing/srgb/base" {
                    error-message "Configure SRGB base and range";
                }
                must " . + ../../../../segment-routing/srgb/base <= 499968" {
                    error-message "Label out of range <256-499968>";
                }
                must ". >= 0 and  . <= ../../../../segment-routing/srgb/range" {
                    error-message "Index value out of configured srgb range for OSPF ipv6";
                }
                must "count(../../../../../instance-id[not(instance-id = current()/../../../../instance-id)][segment-routing/srgb/base  +
                        area/interface/segment-routing/index = current()/../../../../segment-routing/srgb/base + current()]) =  0" {
                    error-message "Conflicting labels for OSPF ipv6 across OSPF instances-ids";
                }
                must "count(../../../../../../../../../../instance[not(name = current()/../../../../../../../../../name)]
                            /protocol/ospf/address-family/ipv6/instance-id[segment-routing/srgb/base +
                            area/interface/segment-routing/index = current()/../../../../segment-routing/srgb/base + current()]) =  0" {
                    error-message "Conflicting labels for OSPF ipv6 across OSPF instances";
                }
                must "count(../../../../../../../../../../instance/protocol/bgp/address-family/srgb[base +
                        index = current()/../../../../segment-routing/srgb/base + current()]) =  0" {
                    error-message "Conflicting labels for OSPF ipv6 and BGP";
                }
                must "count(../../../../../../../../../../instance/protocol/bgp/address-family[label = 
                        current()/../../../../segment-routing/srgb/base + current()]) =  0" {
                    error-message "Conflicting labels for OSPF ipv6 and BGP unicast label";
                }
                must "count(../../../../../../../../../../instance/protocol/bgp/address-family/interface[label-base + sid-index =
                        current()/../../../../segment-routing/srgb/base + current()]) =  0" {
                    error-message "Conflicting labels for OSPF ipv6 and BGP interface";
                }
                must "count(../../../../../../../../../static/route/mpls/in-label[. = current()/../../../../segment-routing/srgb/base + current()]) =  0" {
                    error-message "Conflicting labels for OSPF ipv6 and static in-label";
                }
                description
                    "OSPF interface segment index";
                reference
                '{
                    "attribute-getter" : {
                        "attribute" : "sid"
                    }
                }';
            }
        }
    }

    grouping ospf-interface-segment-routing {
        description "OSPF segment-routing grouping";
        container segment-routing {
            description "Segment routing configuration";
            reference
            '{
                "table-getter": {
                    "library": "libospfyang.so",
                    "symbol":  "ospf_get_interface_tbl_templ",
                    "type" :   "ospf_interface_config",
                    "default-attribute": [{"afi": "ipv4"}],
                    "inherit-attribute":["instance_name", "area_id", "interface"]
                }
            }';
            leaf index {
                type uint32;
                must "../../../../segment-routing/srgb/base" {
                    error-message "Configure SRGB base and range";
                }
                must " . + ../../../../segment-routing/srgb/base <= 499968" {
                    error-message "Label out of range <256-499968>";
                }
                must ". >= 0 and  . <= ../../../../segment-routing/srgb/range" {
                    error-message "Index value out of configured srgb range for OSPF ipv4";
                }
                must "count(../../../../../../../../../instance[not(name = current()/../../../../../../../../name)]
                            /protocol/ospf/address-family/ipv4[segment-routing/srgb/base +
                            area/interface/segment-routing/index = current()/../../../../segment-routing/srgb/base + current()]) =  0" {
                    error-message "Conflicting labels for OSPF ipv4 across OSPF instances";
                }
                must "count(../../../../../../../../../instance/protocol/ospf/address-family/ipv6/instance-id[segment-routing/srgb/base +
                            area/interface/segment-routing/index = current()/../../../../segment-routing/srgb/base + current()]) =  0" {
                    error-message "Conflicting labels for OSPF ipv6 and OSPF ipv6";
                }
                must "count(../../../../../../../../../instance/protocol/bgp/address-family/srgb[base + index =
                        current()/../../../../segment-routing/srgb/base + current()]) =  0" {
                    error-message "Conflicting labels for OSPF ipv4 and BGP";
                }
                must "count(../../../../../../../../../instance/protocol/bgp/address-family[label =
                        current()/../../../../segment-routing/srgb/base + current()]) =  0" {
                    error-message "Conflicting labels for OSPF ipv4 and BGP unicast label";
                }
                must "count(../../../../../../../../../instance/protocol/bgp/address-family/interface[label-base + sid-index =
                        current()/../../../../segment-routing/srgb/base + current()]) =  0" {
                    error-message "Conflicting labels for OSPF ipv4 and BGP interface";
                }
                must "count(../../../../../../../../static/route/mpls/in-label[. = current()/../../../../segment-routing/srgb/base + current()]) =  0" {
                    error-message "Conflicting labels for OSPF ipv4 and static in-label";
                }
                description
                    "OSPF interface segment index";
                reference
                '{
                    "attribute-getter" : {
                        "attribute" : "sid"
                    }
                }';
            }
        }
    }

    grouping ospf-interface-timer-v3 {
        description
            "This grouping defines OSPF interface timer related configuration";
        container timer {
            description "OSPF interface timer configuration";
            reference
            '{
                "table-getter": {
                    "library": "libospfyang.so",
                    "symbol":  "ospf_get_interface_v3_tbl_templ",
                    "type" :   "ospf_interface_config",
                    "inherit-attribute":["instance_name", "area_id", "interface"]
                }
            }';
            leaf hello {
                type uint32 {
                    range "1..65534";
                }
                description
                    "OSPF interface hello interval, default: 10";
                reference
                '{
                    "attribute-getter" : {
                        "attribute" : "hello_interval"
                    }
                }';
            }
            leaf dead {
                type uint32 {
                    range "4..65535";
                }
                description
                    "OSPF interface dead interval, default: 40";
                reference
                '{
                    "attribute-getter" : {
                        "attribute" : "router_dead_interval"
                    }
                }';
            }
            leaf wait {
                type uint32 {
                    range "1..255";
                }
                must "(not(../../network-type)) or (../../network-type != 'p2p')" {
                    error-message "Wait timer supported for 'broadcast'";
                }
                description
                    "OSPF interface wait timer";
                reference
                '{
                    "attribute-getter" : {
                        "attribute" : "wait_interval"
                    }
                }';
            }
        }
    }

    grouping ospf-interface-timer {
        description
            "This grouping defines OSPF interface timer related configuration";
        container timer {
            description "OSPF interface timer configuration";
            reference
            '{
                "table-getter": {
                    "library": "libospfyang.so",
                    "symbol":  "ospf_get_interface_tbl_templ",
                    "type" :   "ospf_interface_config",
                    "inherit-attribute":["instance_name", "area_id", "interface"]
                }
            }';
            leaf hello {
                type uint32 {
                    range "1..65535";
                }
                description
                    "OSPF interface hello interval, default: 10";
                reference
                '{
                    "attribute-getter" : {
                        "attribute" : "hello_interval"
                    }
                }';
            }
            leaf dead {
                type uint32 {
                    range "4..262140";
                }
                description
                    "OSPF interface dead interval, default: 40";
                reference
                '{
                    "attribute-getter" : {
                        "attribute" : "router_dead_interval"
                    }
                }';
            }
            leaf wait {
                type uint32 {
                    range "1..255";
                }
                must "(not(../../network-type)) or (../../network-type != 'p2p')" {
                    error-message "Wait timer supported for 'broadcast'";
                }
                description
                    "OSPF interface wait timer";
                reference
                '{
                    "attribute-getter" : {
                        "attribute" : "wait_interval"
                    }
                }';
            }
        }
    }

    grouping ospf-area-timer {
        description
            "This grouping defines OSPF area timer related configuration";
        container timer {
            description "OSPF area timer configuration";
            reference
            '{
                "table-getter": {
                    "library": "libospfyang.so",
                    "symbol":  "ospf_yang_get_area_tbl_templ",
                    "type" :   "ospf_area_config",
                    "default-attribute": [{"afi": "ipv4"}],
                    "inherit-attribute":["instance_name", "area_id"]
                }
            }';
            container spf {
                description "SPF configuration";
                reference
                '{
                    "table-getter": {
                        "library": "libospfyang.so",
                        "symbol":  "ospf_yang_get_area_tbl_templ",
                        "type" :   "ospf_area_config",
                        "default-attribute": [{"afi": "ipv4"}],
                        "inherit-attribute":["instance_name", "area_id"]
                    }
                }';
                leaf initial-delay {
                    type uint32 {
                        range "1..65535";
                    }
                    description
                        "OSPF SPF computation initial delay in milliseconds, default: 50ms";
                    reference
                    '{
                        "attribute-getter" : {
                            "attribute" : "spf_initial_delay"
                        }
                    }';
                }
                leaf short-delay {
                    type uint32 {
                        range "1..65535";
                    }
                    description
                        "OSPF SPF computation short delay in milliseconds, default: 200ms";
                    reference
                    '{
                        "attribute-getter" : {
                            "attribute" : "spf_short_delay"
                        }
                    }';
                }
                leaf long-delay {
                    type uint32 {
                        range "1..65535";
                    }
                    description
                        "OSPF SPF computation long delay in milliseconds, default: 5000ms";
                    reference
                    '{
                        "attribute-getter" : {
                            "attribute" : "spf_long_delay"
                        }
                    }';
                }
                leaf time-to-learn {
                    type uint32 {
                        range "1..65535";
                    }
                    description
                        "OSPF SPF computation time-to-learn delay in milliseconds, default: 500ms";
                    reference
                    '{
                        "attribute-getter" : {
                            "attribute" : "time_to_learn"
                        }
                    }';
                }
                leaf holddown {
                    type uint32 {
                        range "1..65535";
                    }
                    description
                        "OSPF SPF computation holddown interval in milliseconds, default: 10000ms";
                    reference
                    '{
                        "attribute-getter" : {
                            "attribute" : "spf_holddown_interval"
                        }
                    }';
                }
            }
        }
    }


    grouping ospfv3-area-timer {
        description
            "This grouping defines OSPF area timer related configuration";
        container timer {
            description "OSPF area timer configuration";
            reference
            '{
                "table-getter": {
                    "library": "libospfyang.so",
                    "symbol":  "ospf_yang_get_area_v3_tbl_templ",
                    "type" :   "ospf_area_config",
                    "default-attribute": [{"afi": "ipv6"}],
                    "inherit-attribute":["instance_name", "area_id"]
                }
            }';
            container spf {
                description "SPF configuration";
                reference
                '{
                    "table-getter": {
                        "library": "libospfyang.so",
                        "symbol":  "ospf_yang_get_area_v3_tbl_templ",
                        "type" :   "ospf_area_config",
                        "default-attribute": [{"afi": "ipv6"}],
                        "inherit-attribute":["instance_name", "area_id"]
                    }
                }';
                leaf initial-delay {
                    type uint32 {
                        range "1..65535";
                    }
                    description
                        "OSPF SPF computation initial delay in milliseconds, default: 50ms";
                    reference
                    '{
                        "attribute-getter" : {
                            "attribute" : "spf_initial_delay"
                        }
                    }';
                }
                leaf short-delay {
                    type uint32 {
                        range "1..65535";
                    }
                    description
                        "OSPF SPF computation short delay in milliseconds, default: 200ms";
                    reference
                    '{
                        "attribute-getter" : {
                            "attribute" : "spf_short_delay"
                        }
                    }';
                }
                leaf long-delay {
                    type uint32 {
                        range "1..65535";
                    }
                    description
                        "OSPF SPF computation long delay in milliseconds, default: 5000ms";
                    reference
                    '{
                        "attribute-getter" : {
                            "attribute" : "spf_long_delay"
                        }
                    }';
                }
                leaf time-to-learn {
                    type uint32 {
                        range "1..65535";
                    }
                    description
                        "OSPF SPF computation time-to-learn delay in milliseconds, default: 500ms";
                    reference
                    '{
                        "attribute-getter" : {
                            "attribute" : "time_to_learn"
                        }
                    }';
                }
                leaf holddown {
                    type uint32 {
                        range "1..65535";
                    }
                    description
                        "OSPF SPF computation holddown interval in milliseconds, default: 10000ms";
                    reference
                    '{
                        "attribute-getter" : {
                            "attribute" : "spf_holddown_interval"
                        }
                    }';
                }
            }
        }
    }

    grouping ospf-interface-v3 {
        description
            "This grouping defines OSPF interface related configuration";
        list interface {
            key "name";
            description "OSPF interface configuration";
            reference
            '{
                "table-getter": {
                    "library": "libospfyang.so",
                    "symbol":  "ospf_get_interface_v3_tbl_templ",
                    "type" :   "ospf_interface_config",
                    "default-attribute": [{"afi": "ipv6"}],
                    "inherit-attribute":["instance_name", "area_id"]
                }
            }';
            leaf name {
                type string {
                    length "1..64";
                }
                description
                    "Logical interface name";
                reference
                '{
                    "attribute-getter" : {
                        "attribute" : "interface",
                        "expansion-getter" : {
                            "package":"ospf",
                            "method" : "ospf_logical_interface_name_expander"
                        }
                    }
                }';
            }
            leaf metric {
                type uint32 {
                    range "1..65535";
                }
                description
                    "OSPF interface metric, default: 10000";
                reference
                '{
                    "attribute-getter" : {
                        "attribute" : "metric"
                    }
                }';
            }
            leaf router-priority {
                type uint8 {
                    range "0..255";
                }
                description
                    "OSPF interface router priority, default: 1";
                reference
                '{
                    "attribute-getter" : {
                        "attribute" : "router_priority"
                    }
                }';
            }
            leaf network-type {
                type ospf-network-type;
                description
                    "OSPF interface network type";
                reference
                '{
                    "attribute-getter" : {
                        "attribute" : "interface_type"
                    }
                }';
            }
            leaf mtu-ignore {
                type rtb-ospf-types:enable;

                description
                    "Enable mtu ignore for DD packets";
                reference
                    '{
                        "attribute-getter" : {
                            "attribute" : "mtu_ignore"
                        }
                    }';
            }
            leaf ldp-synchronization
            {
                type rtb-ospf-types:enable;
                description
                    "Enable LDP IGP Synchronization, default disable";
                reference
                '{
                    "attribute-getter" : {
                        "attribute" : "ldp_synchronization"
                    }
                }';
            }
            leaf authentication-profile
            {
                type string {
                    length "1..64";
                }
                description
                    "Authentication profile attachment";
                reference
                '{
                    "attribute-getter" : {
                        "attribute" : "auth_profile"
                    }
                }';
            }
            leaf no-authentication-check
            {
                type rtb-ospf-types:enable;
                description
                    "Enable OSPF no authentication check on received packet, default disable";
                reference
                '{
                    "attribute-getter" : {
                        "attribute" : "no_auth_check"
                    }
                }';
            }

            uses ospf-interface-segment-routing-v3;
            uses ospf-interface-timer-v3;
        }
    }


    grouping ospf-interface {
        description
            "This grouping defines OSPF interface related configuration";
        list interface {
            key "name";
            description "OSPF interface configuration";
            reference
            '{
                "table-getter": {
                    "library": "libospfyang.so",
                    "symbol":  "ospf_get_interface_tbl_templ",
                    "type" :   "ospf_interface_config",
                    "default-attribute": [{"afi": "ipv4"}],
                    "inherit-attribute":["instance_name", "area_id"]
                }
            }';
            leaf name {
                type string {
                    length "1..64";
                }
                description
                    "Logical interface name";
                reference
                '{
                    "attribute-getter" : {
                        "attribute" : "interface",
                        "expansion-getter" : {
                            "package":"ospf",
                            "method" : "ospf_logical_interface_name_expander"
                        }
                    }
                }';
            }
            leaf metric {
                type uint32 {
                    range "1..65535";
                }
                description
                    "OSPF interface metric, default: 10000";
                reference
                '{
                    "attribute-getter" : {
                        "attribute" : "metric"
                    }
                }';
            }
            leaf router-priority {
                type uint8 {
                    range "0..255";
                }
                description
                    "OSPF interface router priority, default: 1";
                reference
                '{
                    "attribute-getter" : {
                        "attribute" : "router_priority"
                    }
                }';
            }
            leaf network-type {
                type ospf-network-type;
                description
                    "OSPF interface network type";
                reference
                '{
                    "attribute-getter" : {
                        "attribute" : "interface_type"
                    }
                }';
            }
            leaf mtu-ignore {
                type rtb-ospf-types:enable;

                description
                    "Enable mtu ignore for DD packets";
                reference
                    '{
                        "attribute-getter" : {
                            "attribute" : "mtu_ignore"
                        }
                    }';
            }
            leaf ldp-synchronization
            {
                type rtb-ospf-types:enable;
                description
                    "Enable LDP IGP Synchronization, default disable";
                reference
                '{
                    "attribute-getter" : {
                        "attribute" : "ldp_synchronization"
                    }
                }';
            }
            leaf authentication-profile
            {
                type string {
                    length "1..64";
                }
                description
                    "Authentication profile attachment";
                reference
                '{
                    "attribute-getter" : {
                        "attribute" : "auth_profile"
                    }
                }';
            }
            leaf no-authentication-check
            {
                type rtb-ospf-types:enable;
                description
                    "Enable OSPF no authentication check on received packet, default disable";
                reference
                '{
                    "attribute-getter" : {
                        "attribute" : "no_auth_check"
                    }
                }';
            }

            uses ospf-interface-segment-routing;
            uses ospf-interface-timer;
        }
    }

    grouping ospf-area {
        description
            "This grouping defines OSPF area related configuration";
        list area {
            key "area-id";
            description "OSPF area configuration";
            reference
            '{
                "table-getter": {
                    "library": "libospfyang.so",
                    "symbol":  "ospf_yang_get_area_tbl_templ",
                    "type" :   "ospf_area_config",
                    "default-attribute": [{"afi": "ipv4"}],
                    "inherit-attribute":["instance_name"]
                }
            }';
            leaf area-id {
                type inet:ipv4-address-no-zone;
                description
                    "OSPF Area Identifier";
                reference
                '{
                    "attribute-getter" : {
                        "attribute" : "area_id"
                    }
                }';
            }
            leaf area-type {
                type ospf-area-type;
            must "(../area-id != '0.0.0.0') or " +
                 "(../area-id = '0.0.0.0' and current() != 'stub' and current() != 'totally-stub')" {
                error-message "area-type can not be 'stub/totally-stub' for area 0.0.0.0";
            }
                description
                    "OSPF Area type";
                reference
                '{
                    "attribute-getter" : {
                        "attribute" : "area_type"
                    }
                }';
            }
            leaf metric {
                type uint32 {
                    range "1..65535";
                }
                description
                    "Area scope default metric, default: 10000";
                reference
                '{
                    "attribute-getter" : {
                        "attribute" : "default_metric"
                    }
                }';
            }
            leaf authentication-profile
            {
                type string {
                    length "1..64";
                }
                description
                    "Authentication profile attachment";
                reference
                '{
                    "attribute-getter" : {
                        "attribute" : "auth_profile"
                    }
                }';
            }
            leaf no-authentication-check
            {
                type rtb-ospf-types:enable;
                description
                    "Enable OSPF no authentication check on received packet, default disable";
                reference
                '{
                    "attribute-getter" : {
                        "attribute" : "no_auth_check"
                    }
                }';
            }
            uses ospf-interface;
            uses ospf-area-timer;
        }
    }

    grouping ospf-area-v3 {
        description
            "This grouping defines OSPF area related configuration";
        list area {
            key "area-id";
            description "OSPF area configuration";
            reference
            '{
                "table-getter": {
                    "library": "libospfyang.so",
                    "symbol":  "ospf_yang_get_area_v3_tbl_templ",
                    "type" :   "ospf_area_config",
                    "default-attribute": [{"afi": "ipv6"}],
                    "inherit-attribute":["instance_name"]
                }
            }';
            leaf area-id {
                type inet:ipv4-address-no-zone;
                description
                    "OSPF Area Identifier";
                reference
                '{
                    "attribute-getter" : {
                        "attribute" : "area_id"
                    }
                }';
            }
            leaf area-type {
                type ospf-area-type;
            must "(../area-id != '0.0.0.0') or " +
                 "(../area-id = '0.0.0.0' and current() != 'stub' and current() != 'totally-stub')" {
                error-message "area-type can not be 'stub/totally-stub' for area 0.0.0.0";
            }
                description
                    "OSPF Area type";
                reference
                '{
                    "attribute-getter" : {
                        "attribute" : "area_type"
                    }
                }';
            }
            leaf metric {
                type uint32 {
                    range "1..65535";
                }
                description
                    "Area scope default metric, default: 10000";
                reference
                '{
                    "attribute-getter" : {
                        "attribute" : "default_metric"
                    }
                }';
            }
            leaf authentication-profile
            {
                type string {
                    length "1..64";
                }
                description
                    "Authentication profile attachment";
                reference
                '{
                    "attribute-getter" : {
                        "attribute" : "auth_profile"
                    }
                }';
            }
            leaf no-authentication-check
            {
                type rtb-ospf-types:enable;
                description
                    "Enable OSPF no authentication check on received packet, default disable";
                reference
                '{
                    "attribute-getter" : {
                        "attribute" : "no_auth_check"
                    }
                }';
            }
            uses ospf-interface-v3;
            uses ospfv3-area-timer;
        }
    }

    grouping ospf-policy {
        description "Policy map name";
        leaf-list policy {
            type string {
                length "1..64";
            }
            must "count(../policy) <= 10"{
                error-message "Maximum of 10 polices are supported in a policy chain";
            }
            ordered-by user;
            description "Policy map name";
            reference
            '{
                "attribute-getter" : {
                    "attribute" : "policy_name"
                }
             }';
        }
    }

    grouping ospf-redistribute {
        description
            "This grouping defines OSPF redistribute related configuration";
        list redistribute {
            key "source";
            description "Redistribution configuration";
            reference
            '{
                "table-getter": {
                    "library": "libospfyang.so",
                    "symbol":  "ospf_yang_get_global_redist_tbl_templ",
                    "type" :   "ospf.redistribution_table",
                    "default-attribute": [{"afi": "ipv4"}],
                    "inherit-attribute":["instance_name"]
                }
            }';
            leaf source {
                type rtb-ospf-types:rib-source;
                description "Source protocol";
                reference
                '{
                    "attribute-getter" : {
                        "attribute" : "source"
                    }
                }';
            }

            leaf metric-type {
                type rtb-ospf-types:metric-type;
                description "External metric type for redistributed routes";
                reference
                '{
                    "attribute-getter" : {
                        "attribute" : "metric_type"
                    }
                }';
            }

            leaf metric {
                type rtb-ospf-types:protocol-metric;
                description "Metric for redistributed routes";
                reference
                '{
                    "attribute-getter" : {
                        "attribute" : "metric"
                    }
                }';
            }
            uses ospf-policy;
        }
    }

    grouping ospf-redistribute-v3 {
        description
            "This grouping defines OSPF redistribute related configuration";
        list redistribute {
            key "source";
            description "Redistribution configuration";
            reference
            '{
                "table-getter": {
                    "library": "libospfyang.so",
                    "symbol":  "ospf_yang_get_global_v3_redist_tbl_templ",
                    "type" :   "ospf.redistribution_table",
                    "default-attribute": [{"afi": "ipv6"}],
                    "inherit-attribute":["instance_name"]
                }
            }';
            leaf source {
                type rtb-ospf-types:rib-source;
                description "Source protocol";
                reference
                '{
                    "attribute-getter" : {
                        "attribute" : "source"
                    }
                }';
            }

            leaf metric-type {
                type rtb-ospf-types:metric-type;
                description "External metric type for redistributed routes";
                reference
                '{
                    "attribute-getter" : {
                        "attribute" : "metric_type"
                    }
                }';
            }

            leaf metric {
                type rtb-ospf-types:protocol-metric;
                description "Metric for redistributed routes";
                reference
                '{
                    "attribute-getter" : {
                        "attribute" : "metric"
                    }
                }';
            }
            uses ospf-policy;
        }
    }

    grouping ospf-segment-routing-v3 {
        description "OSPF Segment routing group";
        container segment-routing {
            description "Segment routing global block configuration";
            reference
            '{
                "table-getter": {
                    "table-name": "global.ospf.instance.config",
                    "type" :   "ospf_instance_config",
                    "default-attribute": [{"afi": "ipv6"}],
                    "inherit-attribute":["instance_name", "instance_id"]
                }
            }';
            leaf status {
                type rtb-types:enable-disable-type;
                description
                    "Segment routing capability";
                reference
                '{
                    "attribute-getter" : {
                        "attribute" : "sr_enabled"
                    }
                }';
            }
            container srgb {
                description "Segment routing global block configuration";
                reference
                '{
                    "table-getter": {
                        "table-name": "global.ospf.instance.config",
                        "type" :   "ospf_instance_config",
                        "default-attribute": [{"afi": "ipv6"}],
                        "inherit-attribute":["instance_name", "instance_id"]
                    }
                }';
                leaf base {
                    type uint32 {
                        range "256 .. 499968" {
                            error-message "OSPF ipv6 srgb base should be between 256 and 499968";
                        }
                    }
                    must "../range" {
                        error-message "SRGB range is not configured";
                    }
                    description
                        "Base label for segment routing global block";
                    reference
                    '{
                        "attribute-getter" : {
                            "attribute" : "srgb_start"
                        }
                    }';
                }
                leaf range {
                    type uint32 {
                        range "0 .. 499968";
                    }
                    must "../base" {
                        error-message "SRGB base is not configured";
                    }
                    description
                        "Range of labels from the segment routing global block base label";
                    reference
                    '{
                        "attribute-getter" : {
                            "attribute" : "srgb_size"
                        }
                    }';
                }
            }
        }
    }

    grouping ospf-segment-routing {
        description "OSPF Segment routing group";
        container segment-routing {
            description "Segment routing global block configuration";
            reference
            '{
                "table-getter": {
                    "table-name": "global.ospf.instance.config",
                    "type" :   "ospf_instance_config",
                    "default-attribute": [{"afi": "ipv4"}],
                    "inherit-attribute":["instance_name"]
                }
            }';
            leaf status {
                type rtb-types:enable-disable-type;
                description
                    "Segment routing capability";
                reference
                '{
                    "attribute-getter" : {
                        "attribute" : "sr_enabled"
                    }
                }';
            }
            container srgb {
                description "Segment routing global block configuration";
                reference
                '{
                    "table-getter": {
                        "table-name": "global.ospf.instance.config",
                        "type" :   "ospf_instance_config",
                        "default-attribute": [{"afi": "ipv4"}],
                        "inherit-attribute":["instance_name"]
                    }
                }';
                leaf base {
                    type uint32 {
                        range "256 .. 499968" {
                            error-message "BGP srgb base should be between 256 and 499968";
                        }
                    }
                    must "../range" {
                        error-message "SRGB range is not configured";
                    }
                    description
                        "Base label for segment routing global block";
                    reference
                    '{
                        "attribute-getter" : {
                            "attribute" : "srgb_start"
                        }
                    }';
                }
                leaf range {
                    type uint32 {
                        range "0 .. 499968";
                    }
                    must "../base" {
                        error-message "SRGB base is not configured";
                    }
                    description
                        "Range of labels from the segment routing global block base label";
                    reference
                    '{
                        "attribute-getter" : {
                            "attribute" : "srgb_size"
                        }
                    }';
                }
            }
        }
    }

    grouping ospf-address-family {
        description "This grouping will handle ospf address family type";
        container address-family {
            description "OSPF afi type";
            uses ospf-address-family_ipv4;
            uses ospf-address-family_ipv6;
        }
    }

    grouping ospf-address-family_ipv6 {
        description "This grouping will handle ospf ipv6 address family";
        container ipv6 {
            description "OSPF ipv6 type";
            uses  ospf-instance_id_ipv6;
        }
    }
    grouping ospf-instance_id_ipv6 {
        description "This grouping will handle ospf address family type";
        list instance-id {
            description "OSPF ipv4 afi type";
            key "instance-id";
            reference
            '{
                "table-getter": {
                    "table-name": "global.ospf.instance.config",
                    "type" :   "ospf_instance_config",
                    "default-attribute": [{"afi": "ipv6"}],
                    "inherit-attribute":["instance_name"]
                }
            }';
            leaf instance-id {
                type uint8 {
                    range "0..31";
                }
                description
                    "Instance identifier, default: 0";
                reference
                '{
                    "attribute-getter" : {
                        "attribute" : "instance_id"
                    }
                }';
            }
            leaf router-id {
                type inet:ipv4-address-no-zone;
                description
                    "OSPF Router identifier";
                reference
                '{
                    "attribute-getter" : {
                        "attribute" : "router_id"
                    }
                }';
            }
            leaf hostname {
                type string {
                    length "1..64";
                }
                description
                    "OSPF Router host name";
                reference
                '{
                    "attribute-getter" : {
                        "attribute" : "hostname"
                    }
                }';
            }
            leaf multipath {
                type uint16;
                description
                    "Maximum ECMP paths to be calculated";
                reference
                '{
                    "attribute-getter" : {
                        "attribute" : "multipath"
                    }
                }';
            }
            leaf metric {
                type uint32 {
                    range "1..65535";
                }
                description
                    "Instance scope default metric, default: 10000";
                reference
                '{
                    "attribute-getter" : {
                        "attribute" : "default_metric"
                    }
                }';
            }

            uses ospf-segment-routing-v3;
            uses ospf-redistribute-v3;
            uses ospf-area-v3;
        }
    }

    grouping ospf-address-family_ipv4 {
        description "This grouping will handle ospf address family type";
        container ipv4 {
            description "OSPF ipv4 afi type";
            reference
            '{
                "table-getter": {
                    "table-name": "global.ospf.instance.config",
                    "type" :   "ospf_instance_config",
                    "default-attribute": [{"afi": "ipv4"}],
                    "inherit-attribute":["instance_name"]
                }
            }';
            leaf router-id {
                type inet:ipv4-address-no-zone;
                description
                    "OSPF Router identifier";
                reference
                '{
                    "attribute-getter" : {
                        "attribute" : "router_id"
                    }
                }';
            }
            leaf hostname {
                type string {
                    length "1..64";
                }
                description
                    "OSPF Router host name";
                reference
                '{
                    "attribute-getter" : {
                        "attribute" : "hostname"
                    }
                }';
            }
            leaf opaque-capability {
                type rtb-types:enable-disable-type;
                description
                    "OSPF opaque LSA processing capability";
                reference
                '{
                    "attribute-getter" : {
                        "attribute" : "opaque_capability"
                    }
                }';
            }
            leaf multipath {
                type uint16;
                description
                    "Maximum ECMP paths to be calculated value";
                reference
                '{
                    "attribute-getter" : {
                        "attribute" : "multipath"
                    }
                }';
            }
            leaf metric {
                type uint32 {
                    range "1..65535";
                }
                description
                    "Instance scope default metric, default: 10000";
                reference
                '{
                    "attribute-getter" : {
                        "attribute" : "default_metric"
                    }
                }';
            }

            uses ospf-segment-routing;
            uses ospf-redistribute;
            uses ospf-area;
        }
    }

    grouping ospf-top {
        description
            "This grouping defines top-level OSPF model data";
        container ospf {
            description "Open shortest path first protocol OSPF configuration";
            uses ospf-address-family;
        } //container ospf
    } //grouping ospf-top
}
