submodule rtbrick-access-access-profile {
    yang-version 1.1;
    belongs-to rtbrick-config {
        prefix config;
    }

    organization
      "Rtbrick";
    contact
      "yang-support@rtbrick.com";

    description
        "This sub module contains the top level configurations of dummy access-access-profile config to help rtbrick roles.
  	This must be pre-date the older package";

    revision 2020-01-01 {
        description
          "Dummy access-access-profile file";
    }

    grouping access-access-profile {
        description "Dummy global access-access-profile top level config";
    }
}
