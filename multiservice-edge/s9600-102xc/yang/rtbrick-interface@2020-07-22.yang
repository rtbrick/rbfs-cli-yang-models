submodule rtbrick-interface {
    yang-version 1.1;

    belongs-to rtbrick-config {
       prefix config;
    }

    import ietf-inet-types {
        prefix inet;
    }

    import rtbrick-types {
        prefix "rtb-types";
    }

    import ietf-yang-types {
        prefix ietfyang;
    }

    include rtbrick-forwarding-options;
    include rtbrick-mtu;
    include rtbrick-network-instance;
    include rtbrick-l2x;

    organization
      "Rtbrick";
    contact
      "yang-support@rtbrick.com";

    description
        "This module describes a YANG model for interface configuration.
        It is tailored for Rtbrick This model supports the following
        INTERFACE configuration level hierarchy:

        +-> { interface }
            +-> subinterface-top
                +-> { subinterface-address-config }
                +-> { subinterface-neighbor-config }
                +-> { state }
            +-> memif-top
            +-> state";

    revision 2020-07-22 {
       description
          "First revision of interface configuration";
        reference "None";
    }

    typedef type-up-down {
        type enumeration {
            enum "down" {
                value 0;
                description
                    "Ready to pass packets";
            }
            enum "up" {
                value 1;
                description
                    "Not ready to pass packets and not in some test mode";
            }
        }
        description "up/down data type";
    }

    typedef rpf-mode {
        type enumeration {
            enum "loose" {
                value 1;
                description
                    "rpf loose";
            }
            enum "strict" {
                value 2;
                description
                    "rpf strict";
            }
        }
        description "rpf modes supported";
    }

    typedef interface-typedef {
        type enumeration {
            enum "l2vpn-vpws" {
                value 1;
                description
                    "Interface type l2vpn-vpws is set";
            }
        }
        description "l2 interface type data type";
    }

    typedef service-meta-data-typedef {
        type enumeration {
            enum "type-1" {
                value 5;
                description
                    "Layer2 service egress meta-data value";
            }
        }
        description "Layer2 service egress meta-data value";
    }

    typedef vlan-operation-typedef {
        type enumeration {
            enum "push" {
                value 1;
                description
                    "Add Vlan";
            }
            enum "pop" {
                value 2;
                description
                    "Delete Vlan";
            }
            enum "swap" {
                value 3;
                description
                    "Swap Vlan";
            }

            enum "push-push" {
                value 4;
                description
                    "Swap Vlan";
            }

            enum "pop-pop" {
                value 5;
                description
                    "Swap Vlan";
            }

            enum "swap-swap" {
                value 6;
                description
                    "Swap Vlan";
            }

            enum "swap-push" {
                value 7;
                description
                    "Swap Vlan";
            }

            enum "pop-swap" {
                value 8;
                description
                    "Swap Vlan";
            }
        }
        description "Vlan operations supported";
    }

    typedef match-typedef {
        type enumeration {
            enum "port" {
                value 1;
                description
                    "Match type port based is set";
            }
        }
        description "l2 interface type data type";
    }

    typedef type-breakout-mode {
        type enumeration {
            enum "4x10G" {
                value 5;
                description "4x10G";
            }
            enum "4x25G" {
                value 6;
                description "4x25G";
            }
        }
        description "breakout data type";
    }

    typedef type-port-speed {
        type enumeration {
            enum "100M" {
                value 100;
                description "100M";
            }
            enum "1G" {
                value 1000;
                description "1G";
            }
            enum "10G" {
                value 10000;
                description "10G";
            }
            enum "25G" {
                value 25000;
                description "25G";
            }
            enum "40G" {
                value 40000;
                description "40G";
            }
            enum "100G" {
                value 100000;
                description "100G";
            }
        }
        description "speed data type";
    }


    typedef type-fec-type {
        type enumeration {
            enum "none" {
                value 1;
                description "none";
            }
            enum "base-r" {
                value 2;
                description "baser";
            }
            enum "rsfec" {
                value 3;
                description "rsfec";
            }
            enum "rs544" {
                value 4;
                description "rs544";
            }
            enum "rs272" {
                value 5;
                description "rs272";
            }
            enum "rs206" {
                value 6;
                description "rs206";
            }
            enum "rs108" {
                value 7;
                description "rs108";
            }
            enum "rs545" {
                value 8;
                description "rs545";
            }
            enum "rs304" {
                value 9;
		description "rs304";
            }
        }
        description "ifp fec type";
    }

    typedef type-holddown-mode {
        type enumeration {
            enum "disable" {
                value 0;
                description "disable";
            }
            enum "enable" {
                value 1;
                description "enable";
            }
        }
        description "ifp holddown mode";
    }

    typedef type-holddown-timer {
        type enumeration {
            enum "0" {
                value 0;
                description "0 ms";
            }
            enum "100" {
                value 100;
                description "100 ms";
            }
            enum "200" {
                value 200;
                description "200 ms";
            }
            enum "500" {
                value 500;
                description "500 ms";
            }
            enum "1000" {
                value 1000;
                description "1s";
            }
            enum "2000" {
                value 2000;
                description "2s";
            }
            enum "5000" {
                value 5000;
                description "5s";
            }
            enum "10000" {
                value 10000;
                description "10s";
            }
        }
    }

    typedef vlan-range {
        type uint16 {
            range "2 .. 4094";
        }
        description "Vlan range";
    }

    typedef type-none {
        type enumeration {
            enum "none" {
                value 1;
                description
                    "Ignore Operation";
            }
        }
        description "Ignore Operation";
    }

    grouping subinterface-address-config {
        description
            "Configuration data for subinterfaces address";

        container address {
	        presence address;
            description
                "Configure ipv4 and ipv6 address for sub-interface";

            reference
                '{
                    "table-getter": {
                        "table-name" : "global.interface.logical.config",
                        "type" :  "ifl_config_table",
                        "inherit-attribute" : [ "ifp_name" , "logical_unit_id" ]
                    }
                }';
            leaf ipv6-link-local {
                description "Configure link-local address for sub-interface";
                type inet:ipv6-address;
                reference
                    '{
                        "attribute-getter": {
                            "attribute" : "ipv6_link_local"
                        }
                    }';
                must 'not(contains(../../../name, "lo-"))' {
                    error-message "Link-local address cannot be configured for loopback interface";
                }
            }
            list ipv4
            {
		        must 'count(../ipv4) - count(../ipv4[secondary="true"]) = 1' {
                    error-message "Primary ipv4 prefix configuration is mandatory and only 1 primary ipv4 prefix is allowed";
                }
                key "prefix4";
                description
                    "Configure ipv4 address under sub-interface";
                ordered-by user;
                reference
                    '{
                        "table-getter": {
                            "table-name": "global.interface.address.config",
                            "type" :  "ifa_config_table",
                            "inherit-attribute" : [ "ifp_name", "logical_unit_id" ]
                        }
                    }';

                leaf prefix4 {
                    type inet:ipv4-prefix;
                    description
                        "Configure ipv4 address";
                    reference
                    '{
                            "attribute-getter" : {
                                "attribute" : "prefix4"
                            }
                     }';
                }
                leaf secondary {
                    type rtb-types:boolean-true;
                    description
                        "Configure type of ipv4 address";
                    reference
                    '{
                            "attribute-getter" : {
                                "attribute" : "secondary"
                            }
                     }';
                }
                leaf-list community {
                    type rtb-types:community-type;
                    description
                        "Configure list of community associated with the address";
                    reference
                    '{
                        "attribute-getter" : {
                            "attribute" : "community"
                        }
                    }';
                }
                leaf-list extended-community {
                    type rtb-types:route-target-type;
                    description
                        "Configure list of extended-community associated with the address";
                    reference
                    '{
                        "attribute-getter" : {
                            "attribute" : "extended_community"
                        }
                    }';
                }
                leaf label {
                    type rtb-types:mpls-label;
                    must "((. >= 256 and . <= 499967) or (. >= 999936 and . <= 1048575))" {
                        error-message "Interface label should be between 256 and 499967 or 999936 and 1048575";
                    }
                    must "count(/config:l2x/name/service-label[. = current()]) = 0" {
                        error-message "Conflicting labels for interface ipv4 and l2x service-label";
                    }
                    must "count(/config:instance/protocol/bgp/address-family/srgb[base + index = current()]) = 0" {
                        error-message "Conflicting labels for interface ipv4 and BGP";
                    }
                    must "count(/config:instance/protocol/bgp/address-family[label = current()]) = 0" {
                        error-message "Conflicting labels for interface ipv4 and BGP unicast label";
                    }
                    must "count(/config:instance/protocol/bgp/address-family/interface[label-base + sid-index = current()]) = 0" {
                        error-message "Conflicting labels for interface ipv4 and BGP interface";
                    }
                    must "count(/config:instance/protocol/isis[segment-routing/srgb/base +
                            interface/segment-routing/ipv4/index = current()]) = 0" {
                        error-message "Conflicting labels for interface ipv4 and ISIS ipv4";
                    }
                    must "count(/config:instance/protocol/isis[segment-routing/srgb/base +
                            interface/segment-routing/ipv6/index = current()]) = 0" {
                        error-message "Conflicting labels for interface ipv4 and ISIS ipv6";
                    }
                    must "count(/config:instance/protocol/ospf/address-family/ipv4[segment-routing/srgb/base +
                            area/interface/segment-routing/index = current()]) = 0" {
                        error-message "Conflicting labels for interface ipv4 and OSPF ipv4";
                    }
                    must "count(/config:instance/protocol/ospf/address-family/ipv6/instance-id[segment-routing/srgb/base +
                            area/interface/segment-routing/index = current()]) = 0" {
                        error-message "Conflicting labels for interface ipv4 and OSPF ipv6";
                    }
                    description
                        "Configure label associated with the address [Range: <256-499967> or <999936-1048575>]";
                    reference
                        '{
                            "attribute-getter" : {
                                "attribute" : "label"
                            }
                        }';
                }
                leaf no-local-routing {
                    type rtb-types:boolean-true;
                    description
                        "Disable local routing";
                    must '(contains(../../../../name, "lo-"))' {
                        error-message "no-local-routing is supported only for loopback interface";
                    }
                    reference
                    '{
                            "attribute-getter" : {
                                "attribute" : "no_local_routing"
                        }
                    }';
                }
            }
            list ipv6
            {
                key "prefix6";
                description
                    "Configure ipv6 address under sub-interface";
                reference
                    '{
                        "table-getter": {
                            "table-name": "global.interface.address.config",
                            "type" :  "ifa_config_table",
                            "inherit-attribute" : [ "ifp_name", "logical_unit_id" ]
                        }
                    }';

                leaf prefix6 {
                    type inet:ipv6-prefix;
                    description
                        "Configure ipv6 address under sub-interface";
                    reference
                    '{
                            "attribute-getter" : {
                                "attribute" : "prefix6"
                            }
                     }';
                }
                leaf-list community {
                    type string {
                        length "1..64";
                    }
                    description
                        "Configure list of community associated with the address";
                    reference
                    '{
                        "attribute-getter" : {
                            "attribute" : "community"
                        }
                    }';
                }
                leaf-list extended-community {
                    type string {
                        length "1..64";
                    }
                    description
                        "Configure list of extended-community associated with the address";
                    reference
                    '{
                        "attribute-getter" : {
                            "attribute" : "extended_community"
                        }
                    }';
                }
                leaf label {
                    type rtb-types:mpls-label;
                    must "((. >= 256 and . <= 499967) or (. >= 999936 and . <= 1048575))" {
                        error-message "Interface label should be between 256 and 499967 or 999936 and 1048575";
                    }
                    must "not(current() =../../ipv4/label)" {
                        error-message "Conflicting labels for interface ipv4 and ipv6";
                    }
                    must "count(/config:instance/static/route/mpls/in-label[. = current()]) = 0" {
                        error-message "Conflicting labels for interface ipv6 and static in-label";
                    }
                    must "count(/config:l2x/name/service-label[. = current()]) = 0" {
                        error-message "Conflicting labels for interface ipv6 and l2x service-label";
                    }
                    must "count(/config:instance/protocol/bgp/address-family/srgb[base + index = current()]) = 0" {
                        error-message "Conflicting labels for interface ipv6 and BGP";
                    }
                    must "count(/config:instance/protocol/bgp/address-family[label = current()]) = 0" {
                        error-message "Conflicting labels for interface ipv6 and BGP unicast label";
                    }
                    must "count(/config:instance/protocol/bgp/address-family/interface[label-base + sid-index = current()]) = 0" {
                        error-message "Conflicting labels for interface ipv6 and BGP interface";
                    }
                    must "count(/config:instance/protocol/isis[segment-routing/srgb/base +
                            interface/segment-routing/ipv4/index = current()]) = 0" {
                        error-message "Conflicting labels for interface ipv6 and ISIS ipv4";
                    }
                    must "count(/config:instance/protocol/isis[segment-routing/srgb/base +
                            interface/segment-routing/ipv6/index = current()]) = 0" {
                        error-message "Conflicting labels for interface ipv6 and ISIS ipv6";
                    }
                    must "count(/config:instance/protocol/ospf/address-family/ipv4[segment-routing/srgb/base +
                            area/interface/segment-routing/index = current()]) = 0" {
                        error-message "Conflicting labels for interface ipv6 and OSPF ipv4";
                    }
                    must "count(/config:instance/protocol/ospf/address-family/ipv6/instance-id[segment-routing/srgb/base +
                            area/interface/segment-routing/index = current()]) = 0" {
                        error-message "Conflicting labels for interface ipv6 and OSPF ipv6";
                    }
                    description
                        "Configure label associated with the address [Range: <256-499967> or <999936-1048575>]";
                    reference
                        '{
                            "attribute-getter" : {
                                "attribute" : "label"
                            }
                        }';
                }
            }
        }  // list address
    }  // grouping subinterface-address-config

    grouping subinterface-neighbor-config {
        description
            "Configuration data for subinterfaces neighbor address";

        container neighbor {
	        presence neighbor;
            description
                "Configure ipv4 and ipv6 neighbor for sub-interface";

            list ipv4
            {
                key "address4";
                description
                    "Configure ipv4 neighbor under sub-interface";
                reference
                    '{
                        "table-getter": {
                            "table-name": "global.static.neighbor.config",
                            "type" :  "static_nbr_cfg_table",
                            "inherit-attribute" : [ "ifp_name", "logical_unit_id" ]
                        }
                    }';

                leaf address4 {
                    type inet:ipv4-address;
                    must "((../mac) or (../dynamic = 'true'))" {
                        error-message "mac address or dynamic mac configuration is mandatory if neighbor ipv4 is configured";
                    }
                    description
                        "Configure ipv4 address";
                    reference
                    '{
                            "attribute-getter" : {
                                "attribute" : "address4"
                            }
                     }';
                }
                choice mac-config {
                    case static {
                        description
                            "Configure MAC address of neighbor statically or dynamically.";
                        leaf mac {
                            type ietfyang:mac-address;
                            description
                                "Configure mac address of neighbor";
                            reference
                            '{
                                    "attribute-getter" : {
                                        "attribute" : "mac_address"
                                    }
                            }';
                        }
                    }
                    case dynamic {
                        leaf dynamic {
                            type rtb-types:boolean-true;
                            description "Dynamic MAC address configuration.";
                            reference
                            '{
                                    "attribute-getter" : {
                                        "attribute" : "dynamic"
                                    }
                            }';
                        }
                    }
                }

            }
            list ipv6
            {
                key "address6";
                description
                    "Configure ipv6 neighbor under sub-interface";
                reference
                    '{
                        "table-getter": {
                            "table-name": "global.static.neighbor.config",
                            "type" :  "static_nbr_cfg_table",
                            "inherit-attribute" : [ "ifp_name", "logical_unit_id" ]
                        }
                    }';

                leaf address6 {
                    type inet:ipv6-address;
                    must "((../mac) or (../dynamic = 'true'))" {
                        error-message "mac address or dynamic mac configuration is mandatory if neighbor ipv6 is configured";
                    }
                    description
                        "Configure ipv6 address";
                    reference
                    '{
                            "attribute-getter" : {
                                "attribute" : "address6"
                            }
                     }';
                }
                choice mac-config {
                    case static {
                        description
                            "Configure MAC address of neighbor statically or dynamically.";
                        leaf mac {
                            type ietfyang:mac-address;
                            description
                                "Configure mac address of neighbor";
                            reference
                            '{
                                    "attribute-getter" : {
                                        "attribute" : "mac_address"
                                    }
                            }';
                        }
                    }
                    case dynamic {
                        leaf dynamic {
                            type rtb-types:boolean-true;
                            description "Dynamic MAC address configuration.";
                            reference
                            '{
                                    "attribute-getter" : {
                                        "attribute" : "dynamic"
                                    }
                            }';
                        }
                    }
                }
            }
        }  // list neighbor
    }  // grouping subinterface-neighbor-config

    grouping subinterface-top {
        description
        "Subinterface data for logical interfaces associated with a
            given interface";

        list unit
        {
            key "unit-id";
            description
                "Configure sub-interface under the physical interface";
            reference
                '{
                    "table-getter": {
                        "table-name": "global.interface.logical.config",
                        "type" :  "ifl_config_table",
                        "inherit-attribute" : [ "ifp_name" ]
                    }
                }';
            leaf unit-id {
                type uint16;
                description
                    "Configure unit which identifies sub-interface under physical interface";
                reference
                '{
                    "attribute-getter" : {
                        "attribute" : "logical_unit_id"
                    }
                }';
            }

            leaf interface-type {
                type interface-typedef;
                description
                    "Configure L2 interface type";
                reference
                '{
                    "attribute-getter" : {
                        "attribute" : "interface_type"
                    }
                }';
            }

            leaf service-meta-data {
                type service-meta-data-typedef;
                description
                    "Configure layer2 service egress meta data value";
                reference
                '{
                    "attribute-getter" : {
                        "attribute" : "ifl_meta_data"
                    }
                }';
            }

            leaf match-type {
                type match-typedef;

                description
                    "Configure match types for the port";
                reference
                '{
                    "attribute-getter" : {
                        "attribute" : "match_type"
                    }
                }';
                must '(../interface-type = "l2vpn-vpws") and (. = "port") and (count(../vlan) = 0 and count(../inner-vlan) = 0)' {
                    error-message "The match-type port is configurable only on a l2vpn-vpws untagged interface.";
                }
            }

            container input-vlan-map {
	            presence input-vlan-map;
                description "Configure Input Vlan Mapping";
                reference
                    '{
                        "table-getter": {
                            "table-name" : "global.interface.logical.config",
                            "type" :  "ifl_config_table",
                            "inherit-attribute" : [ "ifp_name" , "logical_unit_id" ]
                        }
                    }';

                leaf vlan-operation {
                    type vlan-operation-typedef;
                    description
                        "Vlan operation at ingress";
                    must '(../../interface-type = "l2vpn-vpws")' {
                        error-message "Configuration supported only for l2vpn-vpws interface";
                    }
                    must '((.!= "pop") and (.!= "pop-pop")) or not (../vlan-id)' {
                        error-message "Vlan Id is not allowed for this vlan operation";
                    }

                    must 'not ((.!= "pop") and (.!= "pop-pop") and (.!= "pop-swap")) or (../vlan-id)' {
                        error-message "Vlan Id is mandatory for this vlan operation";
                    }

                    must '(.!= "push-push") or (../inner-vlan-id)' {
                        error-message "Inner Vlan Id is mandatory for push-push vlan operation";
                    }

                    must '(.!= "swap-push") or (../inner-vlan-id)' {
                        error-message "Inner Vlan Id is mandatory for swap-push vlan operation";
                    }

                    must '(.!= "swap-swap") or (../inner-vlan-id)' {
                        error-message "Inner Vlan Id is mandatory for swap-swap vlan operation";
                    }
                    must '(.!= "push") or ((not (../inner-vlan-id) and (../vlan-id)) or ((../inner-vlan-id) and not (../vlan-id)))' {
                        error-message "Push is a single vlan operation";
                    }
                    must '(.!= "swap") or ((not (../inner-vlan-id) and (../vlan-id)) or ((../inner-vlan-id) and not (../vlan-id)))' {
                        error-message "Swap is a single vlan operation";
                    }
                    must '(.!="pop-swap") or ((../vlan-id))' {
                        error-message "Vlan Id is mandatory for pop-swap vlan operation";
                    }
                    must '(.!="pop-swap") or not ((../inner-vlan-id))' {
                        error-message "Inner Vlan Id is not allowed for pop-swap vlan operation";
                    }
                    reference
                    '{
                        "attribute-getter" : {
                            "attribute" : "input_vlan_map_vlan_operation"
                        }
                    }';
                }

                leaf vlan-encapsulation {
                    type rtb-types:vlan-encapsulation-type;
                    description
                        "Vlan encapsulation at ingress";
                    must '(../../interface-type = "l2vpn-vpws")' {
                        error-message "Configuration supported only for l2vpn-vpws interface";
                    }

                    must '(../vlan-id)' {
                        error-message "Vlan Id is mandatory for this configuration";
                    }

                    must '(../vlan-operation != "pop-pop") and (../vlan-operation != "pop")' {
                        error-message "Vlan encapsulation is not supported for this vlan operation at ingress.";
                    }

                    reference
                    '{
                        "attribute-getter" : {
                            "attribute" : "input_vlan_map_vlan_encapsulation"
                        }
                    }';
                }

                leaf vlan-id {
                    type vlan-range;
                    description
                        "Configure the vlan for the vlan operation specified";

                    must '(../../interface-type = "l2vpn-vpws")' {
                        error-message "Configuration supported only for l2vpn-vpws interface";
                    }
                    must '(../vlan-operation)' {
                        error-message "Vlan-operation is mandatory";
                    }
                    reference
                    '{
                        "attribute-getter" : {
                            "attribute" : "input_vlan_map_vlan_id"
                        }
                    }';
                }

                leaf inner-vlan-id {
                    type vlan-range;
                    description
                        "Configure the inner vlan for the vlan operation specified";

                    must '(../../interface-type = "l2vpn-vpws")' {
                        error-message "Configuration supported only for l2vpn-vpws interface";
                    }
                    must '(../vlan-id)' {
                        error-message "Vlan-id is mandatory for inner-vlan-id";
                    }
                    must '(../vlan-operation)' {
                        error-message "Vlan-operation is mandatory";
                    }
                    reference
                    '{
                        "attribute-getter" : {
                            "attribute" : "input_vlan_map_inner_vlan_id"
                        }
                    }';
                }
            }
            container output-vlan-map {
	           presence output-vlan-map;
                description "Configure Output Vlan Mapping";
                reference
                    '{
                        "table-getter": {
                            "table-name" : "global.interface.logical.config",
                            "type" :  "ifl_config_table",
                            "inherit-attribute" : [ "ifp_name" , "logical_unit_id" ]
                        }
                    }';

                leaf vlan-operation {
                    type vlan-operation-typedef;
                    description
                        "Vlan operation at egress";
                    must '(../../interface-type = "l2vpn-vpws")' {
                        error-message "Configuration supported only for l2vpn-vpws interface";
                    }

                    must '((.!= "pop") and (.!= "pop-pop")) or not (../vlan-id)' {
                        error-message "Vlan Id is not allowed for this vlan operation";
                    }

                    must 'not ((.!= "pop") and (.!= "pop-pop") and (.!= "pop-swap")) or (../vlan-id)' {
                        error-message "Vlan Id is mandatory for this vlan operation";
                    }

                    must '(.!= "push-push") or ((../vlan-id) and  (../inner-vlan-id))' {
                        error-message "Inner Vlan Id is mandatory for push-push vlan operation";
                    }

                    must '(.!= "swap-push") or ((../vlan-id) and  (../inner-vlan-id))' {
                        error-message "Inner Vlan Id is mandatory for swap-push vlan operation";
                    }

                    must '(.!= "swap-swap") or ((../vlan-id) and  (../inner-vlan-id))' {
                        error-message "Inner Vlan Id is mandatory for swap-swap vlan operation";
                    }
                    must '(.!="pop-swap") or ((../vlan-id))' {
                        error-message "Vlan Id is mandatory for pop-swap vlan operation";
                    }
                    must '(.!="pop-swap") or not ((../inner-vlan-id))' {
                        error-message "Inner Vlan Id is not allowed for pop-swap vlan operation";
                    }
                    must '(.!= "push") or ((not (../inner-vlan-id) and (../vlan-id)) or ((../inner-vlan-id) and not (../vlan-id)))' {
                        error-message "Push is a single vlan operation";
                    }
                    must '(.!= "swap") or ((not (../inner-vlan-id) and (../vlan-id)) or ((../inner-vlan-id) and not (../vlan-id)))' {
                        error-message "Swap is a single vlan operation";
                    }
                    reference
                    '{
                        "attribute-getter" : {
                            "attribute" : "output_vlan_map_vlan_operation"
                        }
                    }';
                }

                leaf vlan-encapsulation {
                    type rtb-types:vlan-encapsulation-type;
                    description
                        "Vlan encapsulation at egress";
                    must '(../../interface-type = "l2vpn-vpws")' {
                        error-message "Configuration supported only for l2vpn-vpws interface";
                    }

                    must '(../vlan-id)' {
                        error-message "Vlan Id is mandatory for this configuration";
                    }

                    must '(../vlan-operation != "pop-pop") and (../vlan-operation != "pop")' {
                        error-message "Vlan encapsulation is not supported for this vlan operation at egress.";
                    }

                    reference
                    '{
                        "attribute-getter" : {
                            "attribute" : "output_vlan_map_vlan_encapsulation"
                        }
                    }';
                }

                leaf vlan-priority-operation {
                    type type-none;
                    description
                        "Vlan Priority operation";
                    must '(../../interface-type = "l2vpn-vpws")' {
                        error-message "Configuration supported only for l2vpn-vpws interface";
                    }
                    reference
                    '{
                        "attribute-getter" : {
                            "attribute" : "output_vlan_map_priority_oper"
                        }
                    }';
                }
                leaf vlan-id {
                    type vlan-range;
                    description
                        "Configure the vlan for the vlan operation specified";

                    must '(../../interface-type = "l2vpn-vpws")' {
                        error-message "Configuration supported only for l2vpn-vpws interface";
                    }
                    must '(../vlan-operation)' {
                        error-message "Vlan-operation is mandatory";
                    }
                    reference
                    '{
                        "attribute-getter" : {
                            "attribute" : "output_vlan_map_vlan_id"
                        }
                    }';
                }

                leaf inner-vlan-id {
                    type vlan-range;
                    description
                        "Configure the inner vlan for the vlan operation specified";

                    must '(../../interface-type = "l2vpn-vpws")' {
                        error-message "Configuration supported only for l2vpn-vpws interface";
                    }
                    must '(../vlan-id)' {
                        error-message "Vlan-id is mandatory for inner-vlan-id";
                    }
                    must '(../vlan-operation)' {
                        error-message "Vlan-operation is mandatory";
                    }
                    reference
                    '{
                        "attribute-getter" : {
                            "attribute" : "output_vlan_map_inner_vlan_id"
                        }
                    }';
                }
            }

            leaf description {
                type rtb-types:string1024;
                description
                    "Configure sub-interface description";
                reference
                '{
                    "attribute-getter" : {
                        "attribute" : "interface_description"
                    }
                }';
            }
            leaf ipv4-admin-status {
                type type-up-down;
                description
                    "Configure sub-interface ipv4 admin status";
                reference
                '{
                    "attribute-getter" : {
                        "attribute" : "ipv4_status"
                    }
                }';
            }
            leaf ipv6-admin-status {
                type type-up-down;
                description
                    "Configure sub-interface ipv6 admin status";
                reference
                '{
                    "attribute-getter" : {
                        "attribute" : "ipv6_status"
                    }
                }';
            }
            leaf mpls-admin-status {
                type type-up-down;
                description
                    "Configure sub-interface mpls admin status";
                reference
                '{
                    "attribute-getter" : {
                        "attribute" : "mpls_status"
                    }
                }';
            }
            container address-translation {
                description "Configure NAT for logical interface";
                presence address-translation;
                reference
                    '{
                        "table-getter": {
                            "table-name": "global.interface.logical.config",
                            "type" :  "ifl_config_table",
                            "inherit-attribute" : [ "ifp_name" , "logical_unit_id" ]
                        }
                    }';
                leaf direction {
                    type enumeration {
                        enum "local" {
                            value 1;
                            description "local / internal";
                        }
                        enum "public" {
                            value 2;
                            description "public / external";
                        }
                    }
                    mandatory true;
                    description "NAT direction";
                    reference
                    '{
                        "attribute-getter" : {
                            "attribute" : "nat_direction"
                        }
                    }';
                }
                leaf profile {
                    type string {
                        length "1..64";
                    }
                    description "NAT profile";
                    must '../direction="local"' {
                        error-message "NAT profile can be configured only if direction is 'local'";
                    }
                    reference
                    '{
                        "attribute-getter" : {
                            "attribute" : "nat_profile_name",
                            "expansion-getter" : {
                                "package":"ifm",
                                "method" :"ifm_nat_profile_name_expander"
                            }
                        }
                    }';
                }
            }
            leaf ipv4-mtu-profile {
                type rtb-types:string64;
                description
                    "Configure sub-interface's ipv4 maximum transmission unit profile";
                must '. = ../../../forwarding-options/mtu-profile/mtu-profile-name' {
                        error-message "MTU profile attached to logical interface is not configured";
                }
                must '../../../forwarding-options/mtu-profile[mtu-profile-name=current()]/type="ipv4"' {
                        error-message "MTU profile attached to logical interface is not of type ipv4";
                }
                reference
                '{
                    "attribute-getter" : {
                        "attribute" : "ipv4_mtu_profile_name",
                        "expansion-getter" : {
                            "package":"ifm",
                            "method" :"ifm_mtu_profile_name_ipv4_expander"
                        }
                    }
                }';
            }
            leaf ipv6-mtu-profile {
                type rtb-types:string64;
                description
                    "Configure sub-interface's ipv6 maximum transmission unit profile";
                must '. = ../../../forwarding-options/mtu-profile/mtu-profile-name' {
                        error-message "MTU profile attached to logical interface is not configured";
                }
                must '../../../forwarding-options/mtu-profile[mtu-profile-name=current()]/type="ipv6"' {
                        error-message "MTU profile attached to logical interface is not of type ipv6";
                }
                reference
                '{
                    "attribute-getter" : {
                        "attribute" : "ipv6_mtu_profile_name",
                        "expansion-getter" : {
                            "package":"ifm",
                            "method" :"ifm_mtu_profile_name_ipv6_expander"
                        }
                    }
                }';
            }
            leaf ip-mtu-profile {
                type rtb-types:string64;
                description
                    "Configure sub-interface's ip maximum transmission unit profile";
                must '. = ../../../forwarding-options/mtu-profile/mtu-profile-name' {
                        error-message "MTU profile attached to logical interface is not configured";
                }
                must '../../../forwarding-options/mtu-profile[mtu-profile-name=current()]/type="ip"' {
                        error-message "MTU profile attached to logical interface is not of type 'ip'";
                }
                reference
                '{
                    "attribute-getter" : {
                        "attribute" : "ip_mtu_profile_name",
                        "expansion-getter" : {
                            "package":"ifm",
                            "method" :"ifm_mtu_profile_name_ip_expander"
                        }
                    }
                }';
            }
            leaf mpls-mtu {
                type uint16;
                //type uint16 {
                //    range "64 .. 1500";
                //}
                description
                    "Configure sub-interface's mpls maximum transmission unit size";
                reference
                '{
                    "attribute-getter" : {
                        "attribute" : "mpls_mtu"
                    }
                }';
            }
            leaf instance {
                type string {
                    length "1..64";
                }
                description
                    "Configure sub-interface's instance name";
                reference
                '{
                    "attribute-getter" : {
                        "attribute" : "instance",
                        "expansion-getter" : {
                            "package":"ifm",
                            "method" :"ifm_instance_name_expander"
                        }
                    }
                }';
            }
            leaf vlan {
                type vlan-range;
                description
                    "Configure sub-interface's outer vlan";
                reference
                '{
                    "attribute-getter" : {
                        "attribute" : "outer_vlan_id"
                    }
                }';
            }
            leaf vlan-encapsulation {
                type rtb-types:vlan-encapsulation-type;
                must "../vlan" {
                    error-message "Vlan configuration is mandatory for vlan-encapsulation";
                }
                description
                    "Configure sub-interface's outer vlan encapsulation";
                reference
                '{
                    "attribute-getter" : {
                        "attribute" : "outer_vlan_encapsulation"
                    }
                }';
            }
            leaf inner-vlan {
                type vlan-range;
                description
                    "Configure sub-interface's inner vlan";
                reference
                '{
                    "attribute-getter" : {
                        "attribute" : "inner_vlan_id"
                    }
                }';
            }
            leaf class-of-service {
                type string {
                    length "1..64";
                }
                description
                    "Configure sub-interface's class-of-service profile name";
                reference
                '{
                    "attribute-getter" : {
                        "attribute" : "qos_profile_name",
                        "expansion-getter" : {
                            "package":"ifm",
                            "method" :"qos_profile_name_expander"
                        }
                    }
                }';
                must 'not(contains(../../name, "lo-"))' {
                    error-message "class-of-service cannot be configured for loopback interface";
                }
            }
            container unnumbered {
                    description
                        "Configure un-numbered loopback interface";

                    reference
                        '{
                            "table-getter": {
                            "table-name": "global.interface.logical.config",
                                "type" :  "ifl_config_table",
                                "inherit-attribute" : [ "ifp_name" , "logical_unit_id" ]
                            }
                        }';

                    leaf interface {
                        type rtb-types:logical-interface-type;
                        description
                            "Configure loopback interface match";
                        reference
                        '{
                            "attribute-getter" : {
                                "attribute" : "unnumbered_ifl",
                                "expansion-getter" : {
                                    "package":"ifm",
                                    "method" :"ifm_interface_logical_name_expander_lo"
                                }
                            }
                        }';
                    }
            }
            must '(count(address/ipv4) = 0 and count(address/ipv6) = 0) or count(unnumbered/interface) = 0' {
                error-message "Unnumbered ifl cannot be configured with an address";
            }

            uses subinterface-address-config;
            uses subinterface-neighbor-config;
            leaf admin-status
            {
                type type-up-down;
                description
                    "User configurable state of sub-interface";
                reference
                    '{
                        "attribute-getter" : {
                            "attribute" : "admin_status"
                        }
                    }';
            }
            leaf garp-disable {
                type rtb-types:boolean-true;
                description
                    "Configure to disable garp";
                reference
                '{
                        "attribute-getter" : {
                            "attribute" : "garp_disable"
                        }
                    }';
            }
            leaf statistics {
                type rtb-types:boolean-type;
                description
                    "Enable traffic-statistic";
                reference
                '{
                        "attribute-getter" : {
                            "attribute" : "statistics"
                    }
                }';
            }
            leaf ra-disable {
                type rtb-types:boolean-true;
                description
                    "Configure to disable ra";
                reference
                '{
                        "attribute-getter" : {
                            "attribute" : "ra_disable"
                    }
                }';
            }
            leaf rpf {
                type rpf-mode;
                description "Configure uRPF mode on logical interface";
                reference
                '{
                    "attribute-getter" : {
                        "attribute" : "ifl_rpf_mode"
                    }
                }';
            }
            leaf neighbor-preference {
                 type uint16 {
                     range "0 .. 300";
                 }
                description "Configure arp-nd preference on logical interface def values:(direct-0, static-5, arp-nd-6, ipoe-7, ppp-8, ldp-9, ospf-10, isis-level-1-15, isis-level-2-18, ibgp-200, ebgp-20)";
                reference
                '{
                    "attribute-getter" : {
                        "attribute" : "neighbor_preference"
                    }
                }';
            }
            must "not(interface-type = 'l2vpn-vpws') or (count(address) = 0 and count(neighbor) = 0 and count(unnumbered/interface) = 0 and count(address-translation) = 0 and count(ip-mtu-profile) = 0 and count(ipv4-admin-status) = 0 and count(ipv4-mtu-profile) = 0 and count(ipv6-admin-status) = 0 and count(ipv6-mtu-profile) = 0 and count(mpls-admin-status) = 0 and count(mpls-mtu) = 0 and count(rpf) = 0)" {
                error-message "Invalid parameters configured on logical interface";
            }
        }  // list subinterface
    }  // grouping subinterface-top

    grouping interface-top {
        description
        "Top-level grouping for interface configuration";

        list interface
        {
            key "name";
            unique "host-if";
            description
               "The list of named interfaces on the device";
            reference
            '{
                "table-getter": {
                    "table-name": "global.interface.physical.config",
                    "type" :  "ifp_config_table"
                }
            }';
            leaf name
            {
                type rtb-types:interface-type;
                description
                    "Configure interface name";
                reference
                '{
                    "attribute-getter" : {
                        "attribute" : "ifp_name",
                        "expansion-getter" : {
                            "package":"ifm",
                            "method" :"ifm_interface_name_expander_without_recyc_ppp_cpu"
                        }
                    }
                }';
            }
            leaf description {
                 type rtb-types:string1024;
                 description
                     "Configure Physical interface description";
                 reference
                 '{
                     "attribute-getter" : {
                         "attribute" : "interface_description"
                     }
                 }';
            }
            leaf auto-negotiation {
                 type rtb-types:boolean-true;
                 description
                     "Configure auto-negotiation feature on interface";
                 reference
                 '{
                     "attribute-getter" : {
                         "attribute" : "auto_negotiation"
                     }
                 }';
            }
            leaf speed {
                 type type-port-speed;
                 description
                     "Configure speed mode for the interface";
                 reference
                 '{
                     "attribute-getter" : {
                         "attribute" : "speed"
                     }
                 }';
            }
            leaf link-training {
                 type rtb-types:boolean-true;
                 description
                     "Configure link training feature on interface";
                 reference
                 '{
                     "attribute-getter" : {
                         "attribute" : "link_training"
                     }
                 }';
            }
            leaf host-if {
                 type string {
                     length "1..64";
                 }
                 description
                     "Configure host_if";
                 reference
                 '{
                     "attribute-getter" : {
                         "attribute" : "hostif_name",
                         "expansion-getter" : {
                             "package":"ifm",
                             "method" :"ifm_veth_inteface_name_expander"
                         }
                     }
                 }';
            }
            leaf mtu-profile {
                 type rtb-types:string64;
                 description
                     "Configure the maximum transmission unit profile on interface";
                 must '. = ../../forwarding-options/mtu-profile/mtu-profile-name' {
                         error-message "MTU profile attached to physical interface is not configured";
                 }
                 must '../../forwarding-options/mtu-profile[mtu-profile-name=current()]/type="physical"' {
                         error-message "MTU profile attached to physical interface is not of type physical";
                 }
                 reference
                 '{
                     "attribute-getter" : {
                         "attribute" : "mtu_profile_name",
                         "expansion-getter" : {
                             "package":"ifm",
                             "method" :"ifm_mtu_profile_name_physical_expander"
                         }
                     }
                 }';
            }
            leaf mru {
                 type uint16 {
                     range "64 .. 9216";
                 }
                 description
                     "Configure the maximum receive unit size on interface";
                 reference
                 '{
                     "attribute-getter" : {
                         "attribute" : "layer2_mru"
                     }
                 }';
            }
            leaf memif-id {
                type uint32;
                description
                    "Configure memif-id , applicable only to memif interface";
                reference
                    '{
                        "attribute-getter" : {
                            "attribute" : "memif_id"
                        }
                    }';
            }
            leaf memif-sock-id {
                type uint32;
                description
                    "Configure memif-sock-id , applicable only to memif interface";
                reference
                    '{
                        "attribute-getter" : {
                            "attribute" : "memif_sock_id"
                        }
                    }';
            }
            leaf master {
                type rtb-types:boolean-type;
                description
                    "Configure memif role as master/slave, applicable only to memif interface";
                reference
                    '{
                        "attribute-getter" : {
                            "attribute" : "is_master"
                        }
                    }';
            }
            leaf admin-status
            {
                type enumeration {
                    enum "down" {
                        value 0;
                        description
                            "Brings down interface";
                    }
                    enum "up" {
                        value 1;
                        description
                            "Brings up interface";
                    }
                }
                description
                    "Configure state of the interface";
                reference
                    '{
                        "attribute-getter" : {
                            "attribute" : "admin_status"
                        }
                    }';
            }
            leaf class-of-service {
                type string {
                    length "1..64";
                }
                description
                    "Configure sub-interface's class-of-service profile name";
                reference
                '{
                    "attribute-getter" : {
                        "attribute" : "qos_profile_name",
                        "expansion-getter" : {
                            "package":"ifm",
                            "method" :"qos_profile_name_expander"
                        }
                    }
                }';
                must 'not(contains(../name, "lo-"))' {
                    error-message "class-of-service cannot be configured for loopback interface";
                }
            }
            leaf forward-error-correction {
                type type-fec-type;
                description
                    "Configure forward error correction";
                reference
                '{
                    "attribute-getter" : {
                        "attribute" : "fec"
                    }
                }';
            }            
            leaf holddown {
                type type-holddown-mode;
                description
                    "Configure to disable holddown machinery";
                reference
                '{
                    "attribute-getter" : {
                        "attribute" : "holddown"
                    }
                }';
            }
            leaf holddown-down-delay {
                type type-holddown-timer;
                description
                    "Configure in unit of ms, overrides default delay of 0ms";
                reference
                '{
                    "attribute-getter" : {
                        "attribute" : "holddown_down"
                    }
                }';
            }
            leaf holddown-up-delay {
                type type-holddown-timer;
                description
                    "Configure in unit of ms, overrides exponential backoff";
                reference
                '{
                    "attribute-getter" : {
                        "attribute" : "holddown_up"
                    }
                }';
            }
            leaf traffic-sampling-profile {
                type rtb-types:string64;
                description
                    "Configure profile string";
                reference
                '{
                        "attribute-getter" : {
                            "attribute" : "traffic_sampling_profile",
                            "expansion-getter" : {
                                 "package":"ifm",
                                 "method" :"ifm_traffic_sampling_profile_name_expander"
                            }
                        }
                 }';
            }
            container ptp {
                description "Configure PTP for physical interface";
                presence ptp;
                reference
                '{
                    "table-getter": {
                        "table-name": "global.interface.physical.config",
                        "type" :  "ifp_config_table",
                        "inherit-attribute" : [ "ifp_name" ]
                    }
                }';
                leaf enable
                {
                    type rtb-types:boolean-true;
                    description
                        "Configure PTP for the interface";

                    must 'not(contains(../../name, "lo-")) and not(contains(../../name, "lag-"))' {
                        error-message "PTP cannot be configured on loopback or LAG interfaces";
                    }

                    reference
                        '{
                            "attribute-getter" : {
                                "attribute" : "ptp"
                            }
                        }';
                }
            }
            container synce {
                description "Configure SyncE for physical interface";
                presence synce;
                reference
                '{
                    "table-getter": {
                        "table-name": "global.interface.physical.config",
                        "type" :  "ifp_config_table",
                        "inherit-attribute" : [ "ifp_name" ]
                    }
                }';
                leaf enable
                {
                    type rtb-types:boolean-true;
                    description
                        "Configure SyncE for the interface";

                    must 'not(contains(../../name, "lo-")) and not(contains(../../name, "lag-"))' {
                        error-message "SyncE cannot be configured on loopback or LAG interfaces";
                    }
                    reference
                        '{
                            "attribute-getter" : {
                                "attribute" : "synce"
                         }
                     }';
                }
                leaf esmc
                {
                    type rtb-types:boolean-true;
                    description
                        "Configure ESMC for the interface";

                    must 'not(contains(../../name, "lo-")) and not(contains(../../name, "lag-"))' {
                        error-message "ESMC cannot be configured on loopback or LAG interfaces";
                    }
                    reference
                        '{
                            "attribute-getter" : {
                                "attribute" : "esmc"
                         }
                    }';
                }
            }
            container breakout {
                description "Configure breakout for physical interface";
                presence breakout;
                reference
                '{
                    "table-getter": {
                        "table-name": "global.interface.physical.config",
                        "type" :  "ifp_config_table",
                        "inherit-attribute" : [ "ifp_name" ]
                    }
                }';
                leaf map
                {
                    type type-breakout-mode;
                    description
                        "Configure breakout for the interface";
                    reference
                        '{
                            "attribute-getter" : {
                                "attribute" : "breakout_mode"
                            }
                        }';
                }
            }
            leaf forward-error-correction-bypass {
                type type-holddown-mode;
                description
                    "Configure to forward error correction bypass";
                reference
                '{
                    "attribute-getter" : {
                        "attribute" : "fec_bypass"
                    }
                }';
            }            
            uses subinterface-top;
        }  // list interface
    }  // grouping interface-top

    grouping global-interface-top {
        description
            "Configuration related to global interface";
        container interface {
	        presence interface;
            description
                "Configuration related to global interface";
            container all {
	            presence all;
                description
                    "Configure interface disable all feature";
                reference
                '{
                    "table-getter": {
                        "table-name": "global.ifmd.config",
                        "type" :  "global_ifmd_config_table",
                        "default-attribute" : [ { "global_interface_all" : "global-interface-all" } ]
                    }
                }';
                leaf admin-status {
                    type enumeration {
                        enum "down" {
                            value 0;
                            description
                                "Brings down interface";
                        }
                        enum "up" {
                            value 1;
                            description
                                "Brings up interface";
                        }
                    }
                    description
                        "Configure state of the interface";
                    reference
                    '{
                        "attribute-getter" : {
                            "attribute" : "status"
                        }
                    }';
                }
                leaf holddown {
                    type type-holddown-mode;
                    description
                        "Configure to disable holddown machinery on all the interfaces";
                    reference
                    '{
                        "attribute-getter" : {
                            "attribute" : "holddown"
                        }
                    }';
                }
            }
        }
    }

    grouping subinterface-set-top {
        description
        "Subinterface data for logical interfaces associated with a
            given interface";

        list unit
        {
            key "unit-id";
            description
                "Configure sub-interface under the physical interface";
            reference
                '{
                    "table-getter": {
                        "table-name": "global.interface.set.member.config",
                        "type" :  "interface_set_member_config_table",
                        "inherit-attribute" : [ "intf_set_name", "ifp_name" ]
                    }
                }';
            leaf unit-id {
                type uint16;
                description
                    "Configure unit which identifies sub-interface under physical interface";
                reference
                '{
                    "attribute-getter" : {
                        "attribute" : "unit_id"
                    }
                }';
            }
        }  // list subinterface
    }  // grouping subinterface-set-top

    grouping interface-name-set-top {
        description
        "Top-level grouping for interface configuration";

        list interface {
            key "name";
            description
                "The list of named interfaces on the device";
            must 'count(../interface) = 1' {
               error-message "Only one physical interface is allowed in interface-set";
            }
            reference
            '{
                "table-getter": {
                    "table-name": "global.interface.set.config",
                    "type" :  "interface_set_config_table",
                    "inherit-attribute" : [ "intf_set_name" ]
                }
            }';
            leaf name
            {
                type rtb-types:interface-type;
                description
                    "Configure interface name";
                reference
                '{
                    "attribute-getter" : {
                        "attribute" : "ifp_name",
                        "expansion-getter" : {
                            "package":"ifm",
                            "method" :"ifm_interface_name_expander_without_recyc_ppp_cpu"
                        }
                    }
                }';
            }
            uses subinterface-set-top;
        }  // list set-interface uses interface-set-subinterface-top;
    }  // grouping interface-set-interface-top

    grouping interface-set-top {
        description
        "Interface Set";

        list interface-set
        {
            key "name";
            description
                "Configure interface-set-name";
            reference
                '{
                    "table-getter": {
                        "table-name": "global.interface.set.name.config",
                        "type" :  "interface_set_name_config_table"
                    }
                }';
            leaf name {
                type string {
                    length "1..64";
                }
                description
                    "Configure interface set";
                reference
                '{
                    "attribute-getter" : {
                        "attribute" : "intf_set_name",
                        "expansion-getter" : {
                            "package":"ifm",
                            "method" :"ifm_intf_set_name_expander"
                        }
                    }
                }';
            }
            leaf class-of-service {
                type string {
                    length "1..64";
                }
                description
                    "Configure sub interface-groupe's class-of-service profile name";
                reference
                '{
                    "attribute-getter" : {
                        "attribute" : "qos_profile_name",
                        "expansion-getter" : {
                            "package":"ifm",
                            "method" :"qos_profile_name_expander"
                        }
                    }
                }';
            }
            uses interface-name-set-top;
        }  // list interface-set add above uses interface-set-interface-top;
    }  // grouping interface-set-top

    uses interface-top;
    uses interface-set-top;
    //uses global-interface-top;
}  // module openconfig-interfaces
