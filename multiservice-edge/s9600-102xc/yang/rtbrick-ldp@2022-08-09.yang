submodule rtbrick-ldp {
    yang-version 1.1;
    belongs-to rtbrick-config {
        prefix config;
    }

    import ietf-inet-types {
        prefix "inet";
    }
    import rtbrick-types {
        prefix "rtb-types";
    }
    import rtbrick-ldp-types {
        prefix "rtb-ldp-types";
    }

    organization "RtBrick";

    contact
      "Authors: Akshath TR (akshath@rtbrick.com)";

    description
        "This module describes a YANG model for LDP configuration.

    This model supports the following LDP configuration level
    hierarchy:

      LDP
        |
        +-> [ Global LDP configuration ]
          +-> Interface
          +-> Peer
            +-> Redistribute";

    revision "2022-08-09" {
      description
        "First revision of LDP configuration";
      reference
        "None";

    }

    grouping ldp-loop-detection {
        container loop-detection {
        description
            "LDP loop detection configurations";
            reference
            '{
                "table-getter": {
                    "table-name": "global.ldp.instance.config",
                    "type" :   "ldp_instance_config_table",
                    "inherit-attribute":["instance_name"]
                }
            }';
            leaf status {
                type rtb-types:enable-disable-type;
                description "Loop detection status";
                reference
                '{
                    "attribute-getter" : {
                        "attribute" : "loop_detection_status"
                    }
                }';
            }
            leaf hop-count {
                type uint8;
                description "Hop count, <1-255>, default 32";
                reference
                '{
                    "attribute-getter" : {
                        "attribute" : "loop_detection_hop_count"
                    }
                }';
            }
            leaf vector-length {
                type uint8;
                description "Max vector length limit, <1-255>, default 32";
                reference
                '{
                    "attribute-getter" : {
                        "attribute" : "loop_detection_vector_length"
                    }
                }';
            }
        } 
    }

    grouping ldp-protocol-preference {
        description "Protocol preference related configuration";
        container protocol-preference {
            description "Protocol preference";
            reference
            '{
                "table-getter": {
                    "table-name": "global.ldp.instance.config",
                    "type" :   "ldp_instance_config_table",
                    "inherit-attribute":["instance_name"]
                }
            }';
            leaf internal {
                type uint32 {
                    range "1..255";
                }
                description
                    "Distance value for internal LDP routes including Link neighbor";
                reference
                '{
                    "attribute-getter" : {
                        "attribute" : "internal_preference"
                    }
                }';
            }
            leaf external {
                type uint32 {
                    range "1..255";
                }
                description
                    "Distance value for Targeted LDP routes";
                reference
                '{
                    "attribute-getter" : {
                        "attribute" : "external_preference"
                    }
                }';
            }
        }
    }

    grouping ldp-policy {
        description "Policy map name";
        leaf-list policy {
            must "count(../policy) <= 10"{
                error-message "Maximum of 10 polices are supported in a policy chain";
            }
            ordered-by user;
            type string {
                length "1..64";
            }
            description "Policy map name";
            reference
            '{
                "attribute-getter" : {
                    "attribute" : "policy_name",
                    "expansion-getter" : {
                        "package":"ldp",
                        "method" : "ldp_policy_name_expander"
                     }
                }
            }';
        }
    }

    grouping ldp-address_family {
        list address-family {
            key "afi safi";
            description "LDP address family";
            reference
            '{
                "table-getter": {
                    "library": "libldpyang.so",
                    "symbol" : "ldp_yang_config_afi_tbl_templ",
                    "type"   : "ldp.afi.config",
                    "inherit-attribute":["instance_name"]
                }
            }';
            leaf afi {
                type rtb-ldp-types:afi;
                description "Afi type";
                reference
                '{
                    "attribute-getter": {
                        "attribute": "afi"
                    }
                }';
            }
            leaf safi {
                type rtb-ldp-types:safi;
                description "Safi type";
                must '(../afi != "l2vpn" and . != "vpls-vpws") or (../afi = "l2vpn" and . = "vpls-vpws")' {
                    error-message "l2vpn afi can only be configured with vpls-vpws safi and vice-versa";
                }                
                reference
                '{
                    "attribute-getter": {
                        "attribute": "safi"
                    }
                }';
            }
            leaf status {
                type rtb-types:enable-disable-type;
                description "Afi status";
                reference
                '{
                    "attribute-getter": {
                        "attribute": "status"
                    }
                }';
            }
            uses ldp-redistribution;
        }
    }

    grouping ldp-redistribution {
        description
            "This grouping defines LDP redistribution related configurations";
        list redistribute {
            key "source";
            description "Redistribution configuration";
            reference
            '{
                "table-getter": {
                    "library": "libldpyang.so",
                    "symbol" : "ldp_yang_config_redist_tbl_templ",
                    "type"   : "ldp.protocolinfra.redistribution_table",
                    "inherit-attribute":["instance_name","afi"]
                }
            }';
            leaf source {
                type rtb-ldp-types:rib-source;
                description "Source protocol";
                reference
                '{
                    "attribute-getter" : {
                        "attribute" : "source"
                    }
                }';
            }
            uses ldp-policy;
        }
    }

    grouping ldp-interface {
        description
            "This grouping defines LDP interface related configuration";
        list interface {
            key "name";
            description "LDP interface configuration";
            reference
            '{
                "table-getter": {
                    "library": "libldpyang.so",
                    "symbol":  "ldp_yang_config_interface_tbl_templ",
                    "type" :   "ldp_interface_config_table"
                }
            }';
            leaf name {
                type string {
                    length "1..64";
                }
                description "Logical interface name";
                reference
                '{
                    "attribute-getter" : {
                        "attribute" : "ifname",
                        "expansion-getter" : {
                            "package":"ldp",
                            "method" : "ldp_ifname_expander"
                        }
                    }
                }';
            }
        }
    }

    grouping ldp-hello {
        container hello {
            description "LDP hello configurations";
            reference
            '{
                "table-getter": {
                    "table-name": "global.ldp.instance.config",
                    "type" :   "ldp_instance_config_table",
                    "inherit-attribute":["instance_name"]
                }
            }';
            leaf interval {
                type uint16;
                description "Hello messages interval, <0-65535>";
                reference
                '{
                    "attribute-getter" : {
                        "attribute" : "discovery_hello_interval"
                    }
                }';
            }
            leaf hold-time {
                type uint16;
                description "Hold interval before declaring a neighbor to be down, <0-65535>";
                reference
                '{
                    "attribute-getter" : {
                        "attribute" : "discovery_hold_interval"
                    }
                }';
            }
        }
    }

    grouping ldp-targeted-hello-timer {
        container targeted-hello {
            description "LDP targeted neighbor configurations";
            reference
            '{
                "table-getter": {
                    "table-name": "global.ldp.instance.config",
                    "type" :   "ldp_instance_config_table",
                    "inherit-attribute":["instance_name"]
                }
            }';
            leaf interval {
                type uint16;
                description "Targeted hello messages interval, <0-65535>, default 15s";
                reference
                '{
                    "attribute-getter" : {
                        "attribute" : "targeted_hello_interval"
                    }
                }';
            }
            leaf hold-time {
                type uint16;
                description "Targeted hold time, <0-65535>, default 45s";
                reference
                '{
                    "attribute-getter" : {
                        "attribute" : "targeted_hold_interval"
                    }
                }';
            }
        }
    }

    grouping ldp-vpws {
        container vpls-vpws {
            description "LDP VPWS Pseudowire configurations";
            list interface {
                key "name";
                unique "pseudowire-id";
                description "Enabling VPWS on an interface";
                reference
                    '{
                        "table-getter": {
                            "library": "libldpyang.so",
                            "symbol": "ldp_yang_config_vpws_tbl_templ",
                            "type" :  "ldp_l2vpn_vpws_intf_config_table"
                        }
                    }';
                
                leaf name {
                    type rtb-types:logical-interface-type;
                    description "Interface name on which VPWS has to be enabled";
                    reference
                        '{
                            "attribute-getter" : {
                                "attribute" : "interface_name",
                                "expansion-getter" : {
                                    "package":"ifm",
                                    "method" : "ifm_interface_layer2_name_expander_from_instance"
                                }
                            }
                        }';
                }

                leaf pseudowire-id {
                    mandatory true;
                    description "VPWS Pseudowire Id";
                    type uint32 {
                        range "1..4294967295";
                    }
                    must '../pseudowire-id' {
                        error-message "Pseudowire ID must be configured";
                    }
                    reference
                        '{
                            "attribute-getter" : {
                                "attribute" : "pseudowire_id"
                            }
                        }';
                }
                
                leaf control-word {
                    description "Enable control word";
                    type rtb-ldp-types:enable-disable;
                    reference
                        '{
                            "attribute-getter" : {
                                "attribute" : "l2_control_flags"
                            }
                        }';
                }

                container neighbor {
                    description "LDP targeted neighbor configuration";
                     container ipv4 {
                        description "IPv4 address configuration";
                        reference
                        '{
                            "table-getter": {
                                "library": "libldpyang.so",
                                "symbol": "ldp_yang_config_vpws_tbl_templ",
                                "type" :  "ldp_l2vpn_vpws_intf_config_table",
                                "inherit-attribute":["interface_name"]
                            }
                        }';
                        leaf address {
                            type inet:ipv4-address-no-zone;
                            description "Targeted neighbor address";
                            must 'not(../../ipv6/address)' {
                                error-message "VPWS neighbor can be either ipv4 or ipv6 address";
                            }                            
                            reference
                            '{
                                "attribute-getter" : {
                                    "attribute" : "nbr_address"
                                }
                            }';
                        }
                    }
                    container ipv6 {
                        description "IPv6 address configuration";
                        reference
                        '{
                            "table-getter": {
                                "library": "libldpyang.so",
                                "symbol": "ldp_yang_config_vpws_tbl_templ",
                                "type" :  "ldp_l2vpn_vpws_intf_config_table",
                                "inherit-attribute":["interface_name"]
                            }
                        }';
                        leaf address {
                            type inet:ipv6-address-no-zone;
                            description "Targeted neighbor address";
                            must 'not(../../ipv4/address)' {
                                error-message "VPWS neighbor can be either ipv4 or ipv6 address";
                            }
                            reference
                            '{
                                "attribute-getter" : {
                                    "attribute" : "nbr_v6_address"
                                }
                            }';
                        }
                    }

                }

                container backup-neighbor {
                    description "LDP backup targeted neighbor configuration";
                    container ipv4 {
                        description "IPv4 address configuration";
                        reference
                        '{
                            "table-getter": {
                                "library": "libldpyang.so",
                                "symbol": "ldp_yang_config_vpws_tbl_templ",
                                "type" :  "ldp_l2vpn_vpws_intf_config_table",
                                "inherit-attribute":["interface_name"]
                            }
                        }';
                        leaf address {
                            type inet:ipv4-address-no-zone;
                            description "Targeted neighbor address";
                            must 'not(../../ipv6/address)' {
                                error-message "VPWS backup neighbor can be either ipv4 or ipv6 address";
                            }
                            must '../../../neighbor/ipv4/address or ../../../neighbor/ipv6/address' {
                                error-message "VPWS neighbor configuration is mandatory for configuring backup VPWS neighbor";
                            }
                            must 'not(../../../neighbor/ipv4/address) or ../../../neighbor/ipv4/address != .' {
                                error-message "VPWS neighbor and Backup neighbor configuration must be different";
                            }                           
                            reference
                            '{
                                "attribute-getter" : {
                                    "attribute" : "backup_nbr_address"
                                }
                            }';
                        }
                    }
                    container ipv6 {
                        description "IPv6 address configuration";
                        reference
                        '{
                            "table-getter": {
                                "library": "libldpyang.so",
                                "symbol": "ldp_yang_config_vpws_tbl_templ",
                                "type" :  "ldp_l2vpn_vpws_intf_config_table",
                                "inherit-attribute":["interface_name"]
                            }
                        }';
                        leaf address {
                            type inet:ipv6-address-no-zone;
                            description "Targeted neighbor address";
                            must 'not(../../ipv4/address)' {
                                error-message "VPWS backup neighbor can be either ipv4 or ipv6 address";
                            }
                            must '../../../neighbor/ipv4/address or ../../../neighbor/ipv6/address' {
                                error-message "VPWS neighbor configuration is mandatory for configuring backup VPWS neighbor";
                            }
                            must 'not(../../../neighbor/ipv6/address) or ../../../neighbor/ipv6/address != .' {
                                error-message "VPWS neighbor and Backup neighbor configuration must be different";
                            }                          
                            reference
                            '{
                                "attribute-getter" : {
                                    "attribute" : "backup_nbr_v6_address"
                                }
                            }';
                        }
                    }
                }
            }
        }
    }

    grouping ldp-targeted-neighbor {
        container targeted-neighbor {
            description "LDP targeted neighbor configuration";
            list ipv4 {
                key "neighbor-address source-address";
                description "IPv4 targeted neighbor";
                reference
                '{
                    "table-getter": {
                        "library": "libldpyang.so",
                        "symbol":  "ldp_yang_config_nbr_tbl_templ",
                        "type" :   "ldp_nbr_config_table"
                    }
                }';
                leaf neighbor-address {
                    type inet:ipv4-address-no-zone;
                    description "Targeted neighbor address";
                    reference
                    '{
                        "attribute-getter" : {
                            "attribute" : "nbr_address"
                        }
                    }';
                }
                leaf source-address{
                    type inet:ipv4-address-no-zone;
                    description "Source address for targeted TCP session";
                    reference
                    '{
                        "attribute-getter" : {
                            "attribute" : "src_address"
                        }
                    }';
                }
                leaf connection-preference {
                    type rtb-ldp-types:afi;
                    description "Transport connection preference";
                    reference
                    '{
                        "attribute-getter" : {
                            "attribute" : "transport_preference"
                        }
                    }';
                }
                leaf neighbor-type {
                    type rtb-ldp-types:nbr-type;
                    description "Neighbor type, sender or receiver";
                    reference
                    '{
                        "attribute-getter" : {
                            "attribute" : "nbr_type"
                        }
                    }';
                }
                leaf interval {
                    type uint16;
                    description "Targeted hello messages interval, <0-65535>, default 15s";
                    reference
                    '{
                        "attribute-getter" : {
                            "attribute" : "hello_interval"
                        }
                    }';
                }
                leaf hold-time {
                    type uint16;
                    description "Targeted hold time, <0-65535>, default 45s";
                    reference
                    '{
                        "attribute-getter" : {
                            "attribute" : "hold_interval"
                        }
                    }';
                }
            }
            list ipv6 {
                key "neighbor-address source-address";
                description "IPv6 targeted neighbor";
                reference
                '{
                    "table-getter": {
                        "library": "libldpyang.so",
                        "symbol":  "ldp_yang_config_nbr_tbl_templ",
                        "type" :   "ldp_nbr_config_table"
                    }
                }';
                leaf neighbor-address {
                    type inet:ipv6-address-no-zone;
                    description "Targeted neighbor address";
                    reference
                    '{
                        "attribute-getter" : {
                            "attribute" : "nbr_v6_address"
                        }
                    }';
                }
                leaf source-address {
                    type inet:ipv6-address-no-zone;
                    description "Source address for targeted TCP session";
                    reference
                    '{
                        "attribute-getter" : {
                            "attribute" : "src_v6_address"
                        }
                    }';
                }
                leaf connection-preference {
                    type rtb-ldp-types:afi;
                    description "Transport connection preference";
                    reference
                    '{
                        "attribute-getter" : {
                            "attribute" : "transport_preference"
                        }
                    }';
                }
                leaf neighbor-type {
                    type rtb-ldp-types:nbr-type;
                    description "Neighbor type, sender or receiver";
                    reference
                    '{
                        "attribute-getter" : {
                            "attribute" : "nbr_type"
                        }
                    }';
                }
                leaf interval {
                    type uint16;
                    description "Targeted hello messages interval, <0-65535>, default 15s";
                    reference
                    '{
                        "attribute-getter" : {
                            "attribute" : "hello_interval"
                        }
                    }';
                }
                leaf hold-time {
                    type uint16;
                    description "Targeted hold time, <0-65535>, default 45s";
                    reference
                    '{
                        "attribute-getter" : {
                            "attribute" : "hold_interval"
                        }
                    }';
                }
            }
        }
    }

    grouping ldp-session {
        container session {
            description "LDP session configurations";
            reference
            '{
                "table-getter": {
                    "table-name": "global.ldp.instance.config",
                    "type" :   "ldp_instance_config_table",
                    "inherit-attribute":["instance_name"]
                }
            }';
            leaf keepalive-interval {
                type uint16 {
                    range "1..65535";
                }
                description "Keepalive messages transmission interval, <1-65535>";
                reference
                '{
                    "attribute-getter" : {
                        "attribute" : "session_keepalive_interval"
                    }
                }';
            }
            leaf keepalive-timeout {
                type uint16 {
                    range "1..65535";
                }
                description "Hold interval before declaring a session to be down, <1-65535>";
                reference
                '{
                    "attribute-getter" : {
                        "attribute" : "session_hold_interval"
                    }
                }';
            }
        }
    }

    grouping ldp-timer {
        container timer {
            description "LDP timers configurations";
            reference
            '{
                "table-getter": {
                    "table-name": "global.ldp.instance.config",
                    "type" :   "ldp_instance_config_table",
                    "inherit-attribute":["instance_name"]
                }
            }';
            uses ldp-hello;
            uses ldp-targeted-hello-timer;
            uses ldp-session;
        }
    }

    grouping igp-synchronization {
        container igp-synchronization {
            description "LDP IGP synchronization configuration";
            reference
            '{
                "table-getter": {
                    "table-name": "global.ldp.instance.config",
                    "type" :   "ldp_instance_config_table",
                    "inherit-attribute":["instance_name"]
                }
            }';
            leaf hold-timer {
                type uint16;
                description "Hold interval before declaring a session to be synchronized, <0-60s>";
                reference
                '{
                    "attribute-getter" : {
                        "attribute" : "igp_sync_hold_time"
                    }
                }';
            }
        }
    }

    grouping source-address {
        container source-address {
            description "LDP source address for TCP session";
            reference
            '{
                "table-getter": {
                    "table-name": "global.ldp.instance.config",
                    "type" :   "ldp_instance_config_table",
                    "inherit-attribute":["instance_name"]
                }
            }';
            leaf ipv4 {
                type inet:ipv4-address-no-zone;
                description "Source address for TCP session";
                reference
                '{
                    "attribute-getter" : {
                        "attribute" : "transport_address"
                    }
                }';
            }
            leaf ipv6 {
                type inet:ipv6-address-no-zone;
                description "Source address for TCP session";
                reference
                '{
                    "attribute-getter" : {
                        "attribute" : "transport_v6_address"
                    }
                }';
            }
        }
    }

    grouping ldp-peer {
        description
            "This grouping defines LDP session related configuration";
        container session {
            description "LDP session related configuration";
            list ipv4 {
                key "address";
                description "ipv4 address";
                reference
                '{
                    "table-getter": {
                        "library": "libldpyang.so",
                        "symbol":  "ldp_yang_config_peer_tbl_templ",
                        "type" :   "ldp_peer_config_table",
                        "inherit-attribute":["instance_name"]
                    }
                }';
                leaf address {
                    type inet:ipv4-address-no-zone;
                    description "LDP peer address";
                    reference
                    '{
                        "attribute-getter": {
                            "attribute": "peer_ipv4_transport_address"
                        }
                    }';
                }
                leaf authentication-id {
                    type string {
                        length "1..64";
                    }
                    description "Authentication Tuple Identifier";
                    reference
                    '{
                        "attribute-getter" : {
                            "attribute" : "auth_id"
                        }
                    }';
                }
                leaf export-policy {
                    type string {
                        length "1..64";
                    }
                    description "Import policy identifier";
                    reference
                    '{
                        "attribute-getter": {
                            "attribute" : "export_policy"
                        }
                    }';
                }
                leaf import-policy {
                    type string {
                        length "1..64";
                    }
                    description "Import policy identifier";
                    reference
                    '{
                        "attribute-getter": {
                            "attribute" : "import_policy"
                        }
                    }';
                }
            }
            list ipv6 {
                key "address";
                description "ipv6 address";
                reference
                '{
                    "table-getter": {
                        "library": "libldpyang.so",
                        "symbol":  "ldp_yang_config_peer_tbl_templ",
                        "type" :   "ldp_peer_config_table",
                        "inherit-attribute":["instance_name"]
                    }
                }';
                leaf address {
                    type inet:ipv6-address-no-zone;
                    description "LDP peer address";
                    reference
                    '{
                        "attribute-getter": {
                            "attribute": "peer_ipv6_transport_address"
                        }
                    }';
                }
                leaf authentication-id {
                    type string {
                        length "1..64";
                    }
                    description "Authentication Tuple Identifier";
                    reference
                    '{
                        "attribute-getter" : {
                            "attribute" : "auth_id"
                        }
                    }';
                }
                leaf export-policy {
                    type string {
                        length "1..64";
                    }
                    description "Import policy identifier";
                    reference
                    '{
                        "attribute-getter": {
                            "attribute" : "export_policy"
                        }
                    }';
                }
                leaf import-policy {
                    type string {
                        length "1..64";
                    }
                    description "Import policy identifier";
                    reference
                    '{
                        "attribute-getter": {
                            "attribute" : "import_policy"
                        }
                    }';
                }
            }
        }
    }

    grouping ldp-top {
        description
            "This grouping defines top-level LDP model data";
        container ldp {
            description "LDP related commands";
            reference
            '{
                "table-getter": {
                    "table-name": "global.ldp.instance.config",
                    "type" :   "ldp_instance_config_table",
                    "inherit-attribute":["instance_name"]
                }
            }';
            leaf router-id {
                type inet:ipv4-address-no-zone;
                description "LDP identifier(format: A.B.C.D)";
                reference
                '{
                    "attribute-getter" : {
                        "attribute" : "local_lsr_id"
                    }
                }';
            }
            leaf connection-preference {
                type rtb-ldp-types:afi;
                description "LDP transport connection preference";
                reference
                '{
                    "attribute-getter" : {
                        "attribute" : "transport_preference"
                    }
                }';
            }
            leaf dual-stack-interop {
                type rtb-types:enable-disable-type;
                description "To interop dual stack TLV with non RFC compliant vendors";
                reference
                '{
                    "attribute-getter" : {
                        "attribute" : "dual_stack_interop"
                    }
                }';
            }

            uses ldp-timer;
            uses ldp-loop-detection;
            uses ldp-protocol-preference;
            uses ldp-targeted-neighbor;
            uses ldp-interface;
            uses igp-synchronization;
            uses source-address;
            uses ldp-address_family;
            uses ldp-peer;
            uses ldp-vpws;
        }
    }
}
