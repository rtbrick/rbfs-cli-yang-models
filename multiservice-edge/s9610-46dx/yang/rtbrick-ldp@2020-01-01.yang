submodule rtbrick-ldp {
    yang-version 1.1;
    belongs-to rtbrick-config {
        prefix config;
    }

    organization
      "Rtbrick";
    contact
      "yang-support@rtbrick.com";

    description
        "This sub module contains the top level configurations of dummy ldp configuration to help rtbrick roles
  	This must be dated before the latest package";

    revision 2020-01-01 {
        description
          "Dummy ldp yang file";
        reference "None";
    }


    grouping ldp-global-top  {
        description "Dummy global ldp top level config";
    }

    grouping ldp-top {
        description "Dummy ldp top level config";

    }
}
