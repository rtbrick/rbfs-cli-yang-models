submodule rtbrick-access-dhcpv6-server {
    yang-version 1.1;
    belongs-to rtbrick-config {
        prefix config;
    }

    organization
      "Rtbrick";
    contact
      "yang-support@rtbrick.com";

    description
        "This sub module contains the top level configurations of dummy access-dhcpv6-server config to help rtbrick roles.
  	This must be pre-date the older package";

    revision 2020-01-01 {
        description
          "Dummy access-dhcpv6-server file";
    }

    grouping access-dhcpv6-server {
        description "Dummy global access-dhcpv6-server top level config";
    }
}
