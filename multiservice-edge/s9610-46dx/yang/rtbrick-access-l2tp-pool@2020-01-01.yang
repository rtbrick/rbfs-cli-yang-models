submodule rtbrick-access-l2tp-pool {
    yang-version 1.1;
    belongs-to rtbrick-config {
        prefix config;
    }

    organization
      "Rtbrick";
    contact
      "yang-support@rtbrick.com";

    description
        "This sub module contains the top level configurations of dummy access-l2tp-pool config to help rtbrick roles.
  	This must be pre-date the older package";

    revision 2020-01-01 {
        description
          "Dummy access-l2tp-pool file";
    }

    grouping access-l2tp-pool {
        description "Dummy global access-l2tp-pool top level config";
    }
}
