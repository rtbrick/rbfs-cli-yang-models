module rtbrick-qos-types {
    yang-version 1.1;
    namespace "urn:types:qos:rtbrick";
    prefix qos-types;

    organization
      "Rtbrick";
    contact
      "yang-support@rtbrick.com";
    description
      "This is the type file containing the common qos types across rtbrick.
      Shall be included in other yang files and used in appropriate places";

    revision 2020-12-16 {
        description
          "This is the first revision of rtbrick yang file";
        reference "None";
    }

    typedef type-qos-string {
        type string {
            length "1..64";
            pattern
                '[_0-9a-zA-Z].*';
        }
        description "Acceptable string type for qos";
    }

    typedef type-qos-class {
        type enumeration {
            enum "class-0" {
                value 0;
                description "Class-0";
            }
            enum "class-1" {
                value 1;
                description "Class-1";
            }
            enum "class-2" {
                value 2;
                description "Class-2";
            }
            enum "class-3" {
                value 3;
                description "Class-3";
            }
            enum "class-4" {
                value 4;
                description "Class-4";
            }
            enum "class-5" {
                value 5;
                description "Class-5";
            }
            enum "class-6" {
                value 6;
                description "Class-6";
            }
            enum "class-7" {
                value 7;
                description "Class-7";
            }
            enum "class-all" {
                value 8;
                description "Class-all";
            }
        }
        description "Qos class data type";
    }

    typedef type-qos-classifier-class {
        type enumeration {
            enum "class-0" {
                value 0;
                description "Class-0";
            }
            enum "class-1" {
                value 1;
                description "Class-1";
            }
            enum "class-2" {
                value 2;
                description "Class-2";
            }
            enum "class-3" {
                value 3;
                description "Class-3";
            }
            enum "class-4" {
                value 4;
                description "Class-4";
            }
            enum "class-5" {
                value 5;
                description "Class-5";
            }
            enum "class-6" {
                value 6;
                description "Class-6";
            }
            enum "class-7" {
                value 7;
                description "Class-7";
            }
        }
        description "Qos classifier class data type";
    }
}
