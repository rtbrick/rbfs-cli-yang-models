submodule rtbrick-access-interface-profile {
    yang-version 1.1;
    belongs-to rtbrick-config {
        prefix config;
    }

    organization
      "Rtbrick";
    contact
      "yang-support@rtbrick.com";

    description
        "This sub module contains the top level configurations of dummy access-interface-profile config to help rtbrick roles.
  	This must be pre-date the older package";

    revision 2020-01-01 {
        description
          "Dummy access-interface-profile file";
    }

    grouping access-interface-profile {
        description "Dummy global access-interface-profile top level config";
    }
}
