submodule rtbrick-pim {
    yang-version 1.1;

    belongs-to rtbrick-config {
        prefix config;
    }

    organization
        "Rtbrick";

    contact
      "yang-support@rtbrick.com";

    description
        "This module contains the dummy YANG model for the PIM protocol configuration";

    revision 2020-01-01 {
        description "First revision of dummy PIM configuration";
        reference "None";
    }

    grouping pim-top {
        description "This grouping define dummy top-level PIM model data";
    }//grouping pim-top
}
