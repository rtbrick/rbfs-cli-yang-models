module rtbrick-igmp-types {
    yang-version 1.1;
    prefix rtb-igmp-types;
    namespace
    "urn:config:rtbrick:igmp:types";

    organization "rtbrick";

    contact
      "yang-support@rtbrick.com";

    description
      "This module contains dummy data type definitions for use in IGMP YANG
    model";

    revision "2020-01-01" {
        description "Dummy IGMP types";
        reference "None";

    }
}
