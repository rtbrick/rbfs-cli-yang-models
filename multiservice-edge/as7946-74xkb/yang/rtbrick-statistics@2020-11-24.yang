submodule rtbrick-statistics {
    yang-version 1.1;

    belongs-to rtbrick-config {
        prefix config;
    }

    organization
      "Rtbrick";

    contact
      "yang-support@rtbrick.com";

    description
      "This module describes the YANG model for the statistics configuration";

    revision 2020-11-24 {
        description
        "Configuration hierarchy for statistics";

        reference "None";
    }

    typedef stats-type {
        type enumeration {
            enum "vpp-node-counters" {
                value 0;
                description "Node counters";
            }
            enum "ifp-counters" {
                value 1;
                description "IFP counters";
            }
            enum "ifl-counters" {
                value 2;
                description "IFL counters";
            }
            enum "qos-queue-counters" {
                value 4;
                description "Queue counters";
            }
            enum "acl-counters" {
                value 6;
                description "ACL counters";
            }
            enum "lag-counters" {
                value 9;
                description "LAG counters";
            }
        }
        description "Statistics data type";
    }

    grouping statistics-top {
        description
            "Top-level statistics configuration";
        container statistics {
	        presence statistics;
            description
                "container for statistics configure";
            list type {
                key "type";
                description
                    "Configuring statistics type";
                reference
                '{
                    "table-getter": {
                        "table-name": "global.statistics.config",
                        "type"    : "statistics_config_table"
                    }
                }';
                leaf type {
                    type stats-type;
                    description
                        "Configure statistics type";
                    reference
                    '{
                        "attribute-getter" : {
                            "attribute" : "stats_type"
                        }
                    }';
                }
                leaf interval {
                    type uint8;
                    description
                        "Configure statistics collection interval";
                    reference
                    '{
                        "attribute-getter" : {
                            "attribute" : "gc_interval"
                        }
                    }';
                }
            }
        }
    }

}
