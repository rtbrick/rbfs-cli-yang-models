submodule rtbrick-access-l2bsa {
    yang-version 1.1;
    belongs-to rtbrick-config {
        prefix config;
    }

    organization
      "Rtbrick";
    contact
      "Authors: Vyshakh (vyshakh@rtbrick.com)";

    description
        "This sub module contains the top level configurations of dummy access-l2bsa config to help rtbrick roles.
  	This must be pre-date the older package";

    revision 2020-01-01 {
        description
          "Dummy access-l2bsa file";
    }

    grouping access-l2bsa {
        description "Dummy global access-l2bsa top level config";
    }
}
