submodule rtbrick-lldp {
    yang-version 1.1;

    belongs-to rtbrick-config {
       prefix config;
    }

    import rtbrick-types {
        prefix "rtb-types";
    }

    organization
      "Rtbrick";
    contact
      "Authors: Vyshakh Krishnan (vyshakh@rtbrick.com)";
    description
      "This sub-module contains the YANG structure for the LLDP module";
    revision 2020-05-19 {
        description "First revision";
        reference "None";
    }

    grouping lldp-top {

        container lldp {
            description "LLDP global configuration";
            reference
            '{
                "table-getter": {
                    "table-name" : "global.lldp.config",
                    "type"    : "lldp_global_config_table",
                    "default-attribute" : [ { "mode" : "global" } ]
                }
            }';
            leaf admin-status {
                type rtb-types:enable-disable-type;
                description "Enable or disable LLDP";
                reference
                '{
                    "attribute-getter" : {
                        "attribute" : "config_status"
                    }
                }';
            }
            leaf system-name {
                type string {
                    length "0..64";
                }
                description "System name";
                reference
                '{
                    "attribute-getter" : {
                        "attribute" : "system_name"
                    }
                }';
            }
            leaf system-description {
                type string {
                    length "0..128";
                }
                description "System description";
                reference
                '{
                    "attribute-getter" : {
                        "attribute" : "system_description"
                    }
                }';
            }
            leaf tx-interval {
                type uint32 {
                    range "1 .. 3600";
                }
                description "LLDP tx interval in seconds(1-3600). Default is 30";
                reference
                '{
                    "attribute-getter" : {
                        "attribute" : "transmit_interval"
                    }
                }';
            }
            leaf tx-hold {
                type uint32  {
                    range "1 .. 360000";
                }
                description "LLDP tx hold count(1-360000). Default is 120";
                reference
                '{
                    "attribute-getter" : {
                        "attribute" : "transmit_holdtime"
                    }
                }';
            }

            list interface {
                key "interface-name";
                description "LLDP interface configuration";
                reference
                '{
                    "table-getter": {
                        "table-name" : "global.lldp.interface.config",
                        "type"    : "lldp_interface_config_table"
                    }
                }';
                leaf interface-name {
                    type string {
                        length "1..64";
                    }
                    description "Interface name";
                    reference
                    '{
                        "attribute-getter" : {
                            "attribute" : "ifp_name",
                            "expansion-getter" : {
                                "package":"lldp",
                                "method" :"lldp_interface_name_expander"
                            }
                        }
                    }';
                }
                leaf port-description {
                    type string {
                        length "0..128";
                    }
                    description "Port description";
                    reference
                    '{
                        "attribute-getter" : {
                            "attribute" : "port_description"
                        }
                    }';
                }
                leaf admin-status {
                    type rtb-types:enable-disable-type;
                    description "Enable or disable LLDP";
                    reference
                    '{
                        "attribute-getter" : {
                            "attribute" : "config_status"
                        }
                    }';
                }
            }
        }
    }
    uses lldp-top;
}
