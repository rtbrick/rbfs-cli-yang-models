submodule rtbrick-resmon {
    yang-version 1.1;

    belongs-to rtbrick-config {
        prefix config;
    }

    import rtbrick-types {
        prefix "rtb-types";
    }
    organization
      "Rtbrick";
    contact
      "yang-support@rtbrick.com";
    description
      "This module describes a YANG model for RESMON daemon configuration";
    revision 2020-08-11 {
        description "First revision";
        reference "None";
    }
    grouping rtb-resmon-top {
        description "Grouping RESMON configuration";
        container resmon {
            description "RESMON daemon configuration hierarchy";
            container optics {
                description "RESMON daemon optics configuration hierarchy";
                list interface {
                    key "interface-name";
                    description "RESMON daemon optic's interface configuration hierarchy";
                    reference
                        '{
                            "table-getter": {
                                "table-name": "global.resmon.optics.config",
                                "type" :  "resmon_optics_config_table"
                            }
                        }';
                    leaf interface-name {
                        type string {
                            length "1..64";
                        }
                        description "Interface name";
                        reference
                            '{
                                "attribute-getter" : {
                                    "attribute" : "port_name",
                                    "expansion-getter" : {
                                        "package":"resmon",
                                        "method" : "resmon_physical_interface_name_expander"
                                    }
                                }
                            }';
                    }
                    leaf high-power-class {
                        type rtb-types:enable-disable-type;
                        description "Enable/Disable high power class for optical module, default enable";
                        reference
                            '{
                                "attribute-getter" : {
                                    "attribute" : "high_power_class_enable"
                                }
                            }';
                    }
                    leaf tx_disable {
                        type rtb-types:boolean-true;
                        description "Disable lasers for optical module, default enable";
                        reference
                            '{
                                "attribute-getter" : {
                                    "attribute" : "tx_disable"
                                }
                            }';
                    }
                }
            }
            container monitoring {
                description "RESMON daemon resource monitoring configuration hierarchy";
                reference
                    '{
                        "table-getter": {
                            "table-name": "global.resmon.config",
                            "type" :  "resmon_config_table",
                            "default-attribute" : [ {"configuration_name" : "monitoring" } ]
                        }
                    }';
                leaf poll-interval {
                    type uint32 {
                        range "3 .. 10000";
                    }
                    description "Poll-interval in seconds for resource to be monitored, default 10s";
                    reference
                        '{
                            "attribute-getter" : {
                                "attribute" : "poll_interval"
                            }
                        }';
                }
            }
        }
    }
    uses rtb-resmon-top;
}
