submodule rtbrick-policy {
    yang-version 1.1;

    belongs-to rtbrick-config {
        prefix config;
    }

    organization "Rtbrick";

    contact
      "yang-support@rtbrick.com";

    description
      "This module describes a YANG model for policy protocol
    configuration.

    This model supports the following policy configuration level
    hierarchy:

      Policy
        |
        +-> Policy-list
        +-> Policy-statement
            +-> ordinal
                +-> match
                    +-> rule
                +-> action
                    +-> rule";

    revision "2020-07-26" {
      description
        "First revision of policy configuration";
      reference
        "None";

    }

    typedef operation {
        type enumeration {
            enum add {
                value "0";
                description "Operation to perform addition";
            }
            enum subtract {
                value "1";
                description "Operation to perform subtraction";
            }
            enum multiply {
                value "2";
                description "Operation to perform multiplication";
            }
            enum divide {
                value "3";
                description "Operation to perform division";
            }
            enum append {
                value "4";
                description "Operation to append existing data with a value";
            }
            enum delete-attribute {
                value "5";
                description "Operation to delete an attribute";
            }
            enum overwrite {
                value "6";
                description "Operation to overwrite existing data with a value";
            }
            enum prepend {
                value "7";
                description "Operation to prepend existing data with a value";
            }
            enum delete-attribute-match {
                value "8";
                description "Operation to delete attribute that matches";
            }
            enum goto-next-ordinal {
                value "9";
                description "Operation to continue executing policy to next ordinal";
            }
            enum return-deny{
                value "10";
                description "Operation to stop executing policy and return deny";
            }
            enum return-permit {
                value "11";
                description "Operation to stop executing policy and return permit";
            }
            enum goto-next-policy {
                value "12";
                description "Operation to continue executing next policy in chain";
            }
        }
        description "Operation enum";
    }

    typedef match-type {
        type enumeration {
            enum exact {
                value "1";
                description "Exact type match";
            }
            enum exists {
                value "2";
                description "Exist type match";
            }
            enum greater {
                value "3";
                description "Greater type match";
            }
            enum greater-or-exact {
                value "4";
                description "Greater or exact type match";
            }
            enum less {
                value "5";
                description "Less type match";
            }
            enum less-or-exact {
                value "6";
                description "Less or exact type match";
            }
            enum prefix-length-exact {
                value "7";
                description "Prefix length exact type match";
            }
            enum prefix-length-greater {
                value "8";
                description "Prefix length greater type match";
            }
            enum prefix-length-greater-or-exact {
                value "9";
                description "Prefix length greater or exact type match";
            }
            enum regex {
                value "10";
                description "Regex type match";
            }
            enum longer {
                value "11";
                description "Longer type match";
            }
            enum or-longer {
                value "12";
                description "Or longer type match";
            }
            enum neighbor {
                value "13";
                description "Neighbor AS in BGP AS-path";
            }
            enum transit {
                value "14";
                description "Transit AS in BGP AS-path";
            }
            enum origin {
                value "15";
                description "Origin AS in BGP AS-path";
            }
        }
        description "Match type enum";
    }

    typedef match-attr-type {
        type enumeration {
            enum equal {
                value "1";
                description "Equal type match";
            }
            enum exists {
                value "2";
                description "Exist type match";
            }
            enum greater {
                value "3";
                description "Greater type match";
            }
            enum greater-or-equal {
                value "4";
                description "Greater or exact type match";
            }
            enum less {
                value "5";
                description "Less type match";
            }
            enum less-or-equal {
                value "6";
                description "Less or exact type match";
            }
            enum regex {
                value "10";
                description "Regex type match";
            }
        }
        description "Attribute match type enum";
    }

    typedef match-count-type {
        type enumeration {
            enum equal {
                value "1";
                description "Equal type match";
            }
            enum greater {
                value "3";
                description "Greater type match";
            }
            enum greater-or-equal {
                value "4";
                description "Greater or equal type match";
            }
            enum less {
                value "5";
                description "Less type match";
            }
            enum less-or-equal {
                value "6";
                description "Less or equal type match";
            }
        }
        description "Match count type enum";
    }

    typedef match-logic {
        type enumeration {
            enum or {
                value "0";
                description "Match condition OR, if one rule matches, policy is considered as pass and action will be executed";
            }
            enum and {
                value "1";
                description "Match condition AND, all rules need to match before policy is considered as pass and action will be executed";
            }
        }
        description "Match type enum";
    }

    typedef value-type {
        type enumeration {
            enum discrete {
                value "0";
                description "Value entered is a fixed value";
            }
            enum list {
                value "1";
                description "Value entered is a list name";
            }
            enum length {
                value "2";
                description "Value entered is length of array";
            }
        }
        description "Match condition enum";
    }

    grouping policy-list-ordinal {
        description "Policy list ordinal group";
        list ordinal {
            key "ordinal";
            unique "value";
            description "Policy list ordinal configuration";
            reference
            '{
                "table-getter": {
                    "table-name": "global.policy.list.entry.config",
                    "type" :  "policy_list_entry_config_table",
                    "inherit-attribute": [ "list_name", "type" ]
                }
            }';
            leaf ordinal {
                type uint32;
                description "Ordinal number";
                reference
                '{
                    "attribute-getter" : {
                        "attribute" : "ordinal"
                    }
                }';
            }
            leaf value {
                type string {
                    length "1..64";
                }
                mandatory true;
                description "Attribute value";
                reference
                '{
                    "attribute-getter" : {
                        "attribute" : "value"
                    }
                }';
            }
            leaf value2 {
                type string {
                    length "1..64";
                }
                must "../../sub-type = 'range'"{
                    error-message "value2 is supported for sub-type range only";
                }
                description "Attribute value2";
                reference
                '{
                    "attribute-getter" : {
                        "attribute" : "value2"
                    }
                }';
            }
        }
    }

    grouping policy-list {
        description "Policy list group";
        list list {
            key "name type";
            description "Policy list configuration";
            reference
            '{
                "table-getter": {
                    "table-name": "global.policy.list.config",
                    "type" :  "policy_list_config_table"
                }
            }';
            leaf name {
                type string {
                    pattern
                        '[a-zA-Z_][a-zA-Z0-9_]{0,64}';
                    length "1..64";
                }

                description "List name";
                reference
                '{
                    "attribute-getter" : {
                        "attribute" : "list_name"
                    }
                }';
            }
            leaf type {
                type enumeration {
                    enum ipv4-prefix {
                        value "0";
                        description "IPv4 prefix list";
                    }
                    enum ipv6-prefix {
                        value "1";
                        description "IPv6 prefix list";
                    }
                    enum ipv4-address {
                        value "30";
                        description "IPv4 address list";
                    }
                    enum ipv6-address {
                        value "31";
                        description "IPv6 address list";
                    }
                    enum route-distinguisher {
                        value "2";
                        description "Route distinguisher list";
                    }
                    enum community {
                        value "3";
                        description "Community list";
                    }
                    enum extended-community {
                        value "4";
                        description "Extended community list";
                    }
                    enum large-community {
                        value "5";
                        description "Large community list";
                    }
                    enum as-path {
                        value "6";
                        description "AS path list";
                    }
                    enum source {
                        value "14";
                        description "Source protocol list";
                    }
                    enum sub-source {
                        value "15";
                        description "Sub source list";
                    }
                    enum cluster-list {
                        value "7";
                        description "Cluster list";
                    }
                    enum mpls-label {
                        value "38";
                        description "MPLS Label list";
                    }
                    enum ipv4-mcast-group {
                        value "32";
                        description "IPv4 multicast group list";
                    }
                }
                description "List type";
                reference
                '{
                    "attribute-getter" : {
                        "attribute" : "type"
                    }
                }';
            }
            leaf sub-type {
                type enumeration {
                    enum range {
                        value "1";
                        description "Configure range of elements";
                    }
                }
                must "../type = 'as-path'"{
                    error-message "sub-type range is supported with type as-path only";
                }
                description "Sub-type of list";
                reference
                '{
                    "attribute-getter" : {
                        "attribute" : "sub_type"
                    }
                }';
            }
            uses policy-list-ordinal;
            must "not(sub-type = 'range') or (count(ordinal[value2]) = count(ordinal))" {
                error-message "When subtype is range, value2 must be configured for all entries.";
            }
            must "(count(ordinal[value]) <= 64000)" {
                error-message "Only 64,000 ordinals are supported in the list";
            }
        }
    }

    grouping policy-match-rule {
        description "Policy match rule group";
        list rule {
            key "rule";
            description "Policy match rule configuration";
            reference
            '{
                "table-getter": {
                    "table-name": "global.policy.match.rules.config",
                    "type" :  "policy_rules_config_table",
                    "inherit-attribute": [ "statement_name", "ordinal" ]
                }
            }';
            leaf rule {
                type uint32;
                description "Rule number";
                reference
                '{
                    "attribute-getter" : {
                        "attribute" : "rule"
                    }
                }';
            }
            leaf type {
                type string {
                    length "1..64";
                }
                description "Attribute-type against which this rule will be judged";
                reference
                '{
                    "attribute-getter" : {
                        "attribute" : "application_type",
                        "expansion-getter" : {
                            "package":"policy",
                            "method" : "policy_match_application_type_expander"
                        }
                    }
                }';
            }
            leaf value-type {
                type value-type;
                description "Value field data type";
                reference
                '{
                    "attribute-getter" : {
                        "attribute" : "value_type"
                    }
                }';
            }
            leaf match-type {
                type match-type;
                description "Matching criteria for mentioned attribute-type";
                reference
                '{
                    "attribute-getter" : {
                        "attribute" : "match_type"
                    }
                }';
            }
            leaf-list value {
                type string {
                    length "1..1024";
                }
                ordered-by user;
                description "Value against which mentioned attribute-type data will be judged";

                must "(../value-type != 'list') or
                      (/config:policy/list[name = current()])" {
                    error-message "A policy list that is not configured or has been deleted is referenced in policy statements.";
                }

                reference
                '{
                    "attribute-getter" : {
                        "attribute" : "value",
                        "expansion-getter" : {
                            "package": "policy",
                            "method" : "policy_list_expander"
                        }
                    }
                }';
            }
        }
    }

    grouping policy-match {
        description "Policy match group";
        container match {
            presence "Match configuration";
            description "Policy match configuration";
            uses policy-match-rule;
        }
    }

    grouping policy-action-rule {
        description "Policy action rule group";
        list rule {
            key "rule";
            description "Policy action rule configuration";
            reference
            '{
                "table-getter": {
                    "table-name": "global.policy.action.rules.config",
                    "type" :  "policy_rules_config_table",
                    "inherit-attribute": [ "statement_name", "ordinal" ]
                }
            }';
            leaf rule {
                type uint32;
                description "Rule number";
                reference
                '{
                    "attribute-getter" : {
                        "attribute" : "rule"
                    }
                }';
            }
            leaf type {
                type string {
                    length "1..64";
                }
                description "Attribute type";
                reference
                '{
                    "attribute-getter" : {
                        "attribute" : "application_type",
                        "expansion-getter" : {
                            "package":"policy",
                            "method" : "policy_set_application_type_expander"
                        }
                    }
                }';
            }
            leaf operation {
                type operation;
                description "Operation to be performed on the mentioned attribute-type";
                reference
                '{
                    "attribute-getter" : {
                        "attribute" : "operation_type"
                    }
                }';
                must "not(. = 'delete-attribute-match') or (../type = 'community' or ../type = 'extended-community' or ../type = 'large-community')" {
                    error-message "Action type 'delete-attribute-match' is supported only for application-type community, extended-community and large-community";
                }
                must "not(. = 'delete-attribute-match') or (../type = ../../../match/rule/type )" {
                    error-message "Match rule is not configured for application-type with action 'delete-attribute-match'";
                }
                must "not(. = 'delete-attribute-match') or (count(../../../match/rule[type = current()/../type][value-type='list']) = 0)" {
                    error-message "Match rule value-type 'list' is not supported with action 'delete-attribute-match";
                }
            }
            leaf-list value {
                type string {
                    length "1..64";
                }
                ordered-by user;
                description "Value which is used for performing the operation on the mentioned attribute-type";

                reference
                '{
                    "attribute-getter" : {
                        "attribute" : "value"
                    }
                }';
            }
        }
    }

    grouping policy-action {
        description "Policy action group";
        container action {
            presence "Action configuration";
            description "Policy action configuration";
            uses policy-action-rule;
        }
    }

    grouping policy-ordinal {
        description "Policy ordinal group";
        list ordinal {
            key "ordinal";
            description "Policy ordinal configuration";
            reference
            '{
                "table-getter": {
                    "table-name": "global.policy.ordinal.config",
                    "type" :  "policy_ordinal_config_table",
                    "inherit-attribute": [ "statement_name" ]
                }
            }';
            leaf ordinal {
                type uint32;
                description "Ordinal number";
                reference
                '{
                    "attribute-getter" : {
                        "attribute" : "ordinal"
                    }
                }';
            }
            leaf description {
                type string {
                    length "1..128";
                }
                description "Ordinal description";
                reference
                '{
                    "attribute-getter" : {
                        "attribute" : "description"
                    }
                }';
            }
            leaf condition {
                type string {
                    length "1..64";
                }
                description "Condition profile name";
                must "count(/config:policy/condition[condition_name = current()]) > 0" {
                    error-message "A policy condition that is not configured or has been deleted is referenced in policy statements.";
                }
                reference
                '{
                    "attribute-getter" : {
                        "attribute" : "condition_profile",
                        "expansion-getter" : {
                            "package": "policy",
                            "method" : "policy_condition_expander"
                        }
                    }
                }';
            }
            leaf match-logic {
                type match-logic;
                description "Match condition type";
                reference
                '{
                    "attribute-getter" : {
                        "attribute" : "condition"
                    }
                }';
            }
            uses policy-match;
            uses policy-action;
        }
    }

    grouping policy-statement {
        description "Policy statement group";
        list statement {
            key "name";
            description "Policy statement configuration";
            reference
            '{
                "table-getter": {
                    "table-name": "global.policy.statement.config",
                    "type" :  "policy_statement_config_table"
                }
            }';
            leaf name {
                type string {
                    pattern
                        '[a-zA-Z_][a-zA-Z0-9_]{0,64}';
                    length "1..64";
                }
                description "Statement name";
                reference
                '{
                    "attribute-getter" : {
                        "attribute" : "statement_name"
                    }
                }';
            }
            must "not((count(./ordinal/match/rule[type = 'ipv4-prefix']) > 0) and (count(./ordinal/match/rule[type = 'ipv6-prefix']) > 0))" {
                error-message "Match rule for ipv4-prefix and ipv6-prefix should not be configured under same policy";
            }
            uses policy-ordinal;
        }
    }

    grouping policy-attribute {
        description "Policy match attribute rule group";
        list attribute {
            key "name";
            description "Condition table attribute match name";
            reference
            '{
                "table-getter": {
                    "table-name": "global.policy.condition.attribute.config",
                    "type" :  "policy_attribute_match_config_table",
                    "inherit-attribute": [ "profile_name" ]
                }
            }';
            leaf name {
                type string {
                    pattern
                        '[a-zA-Z_][a-zA-Z0-9_]{0,64}';
                    length "1..64";
                }
                description "Condition object attribute name";
                reference
                '{
                    "attribute-getter" : {
                        "attribute" : "attribute_name"
                    }
                }';
            }
            leaf match {
                type match-attr-type;
                description "Condition object match type";
                reference
                '{
                    "attribute-getter" : {
                        "attribute" : "match_type"
                    }
                }';
            }
            leaf-list value {
                type string {
                    length "1..64";
                }
                ordered-by user;
                description "Match value for attribute";
                reference
                '{
                    "attribute-getter" : {
                        "attribute" : "match_value"
                    }
                }';
            }
        }
    }


    grouping policy-condition {
        description "Policy condition group";
        list condition {
            key "condition_name";
            description "Policy condition configuration";
            reference
            '{
                "table-getter": {
                    "table-name": "global.policy.condition.config",
                    "type" :  "policy_condition_config_table"
                }
            }';
            leaf condition_name {
                type string {
                    pattern '[a-zA-Z_\.][a-zA-Z0-9_\.]{0,64}';
                    length "1..64";
                }
                description "Condition profile name";

                reference
                '{
                    "attribute-getter" : {
                        "attribute" : "profile_name"
                    }
                }';
            }
            container table {
                description "Policy condition table";
                    reference
                    '{
                        "table-getter": {
                            "table-name": "global.policy.condition.config",
                            "type" :  "policy_condition_config_table",
                            "inherit-attribute":["profile_name"]
                    }
                }';
                leaf name {
                    type string {
                        length "1..128";
                    }
                    description "Table name";
                    reference
                    '{
                        "attribute-getter" : {
                            "attribute" : "table_name"
                        }
                    }';
                }
                leaf bd {
                    type string {
                        length "1..64";
                    }
                    description "BD's name, which resolves the condition";
                    reference
                    '{
                        "attribute-getter" : {
                        "attribute" : "app_name"
                        }
                    }';
                }
                leaf count {

                    type uint32;
                    description "Condition object match count";
                    reference
                    '{
                        "attribute-getter" : {
                            "attribute" : "match_count"
                        }
                    }';
                }
                leaf match {
                    type match-count-type;
                    description "Condition object match type";
                    reference
                    '{
                        "attribute-getter" : {
                            "attribute" : "match_count_type"
                        }
                    }';
                }
            }
            uses policy-attribute;
            }
        }

    grouping policy-top {
        description
            "This grouping define top-level policy model data.";

        container policy {
            description "Policy configuration";
            uses policy-list;
            uses policy-statement;
            uses policy-condition;
        }
    }
    uses policy-top;
}
