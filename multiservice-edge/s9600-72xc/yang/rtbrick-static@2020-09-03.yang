submodule rtbrick-static {
    yang-version 1.1;

    belongs-to rtbrick-config {
       prefix config;
    }

    import ietf-inet-types {
        prefix inet;
    }

    import rtbrick-types {
        prefix "rtb-types";
    }

    organization
      "Rtbrick";
    contact
      "yang-support@rtbrick.com";

    description
        "This module describes a YANG model for static route configuration
        +-> {static}
            +-> {route}
                +-> {ipv4}
                +-> {ipv6}
                +-> {multicast4}
                +-> {mpls}
            +-> {nexthop-profile}
            +-> {route-attributes}
            +-> {conditional-profile}";

    revision 2020-09-03 {
       description
          "First revision of static route configuration";
        reference "None";
    }

    typedef afi {
        type enumeration {
            enum ipv4 {
                value "0";
                description "IPv4 address family";
            }
            enum ipv6 {
                value "1";
                description "IPv6 address family";
            }
            enum mpls {
                value "2";
                description "MPLS address family";
            }
        }
        description "AFI data type";
    }

    typedef route-options {
        type enumeration {
            enum "no-install" {
                value 1;
                description "This Route should not be installed in hardware.";
            }
        }
        description "RouteOptions data type.";
    }

    typedef safi {
        type enumeration {
            enum labeled-unicast {
                value "0";
                description "Labeled unicast";
            }
            enum multicast {
                value "1";
                description "Labeled multicast";
            }
            enum unicast {
                value "2";
                description "Unicast";
            }
        }
        description "SAFI data type";

    }

    typedef compare-type {
        type enumeration {

            enum route-count {
                value "0";
                description "Check configured route count";
            }
            enum bgp-peer-established {
                value "1";
                description "Check configured bgp peer is established";
            }
            enum isis-neighbor-up {
                value "2";
                description "Check configured isis neighbor is up";
            }
            enum any-isis-neighbor-up {
                value "3";
                description "Check any isis neighbor is up in the configured level";
            }
            enum interface-up {
                value "4";
                description "Check interface state is up";
            }
        }
        description "Compare type";
    }

    typedef compare-operation-type {
        type enumeration {
            enum greater-than {
                value "2";
                description "Conditional route compare operation";
            }
        }
        description "Conditional route compare operation";
    }

    typedef match-isis-level-type {
        type enumeration {
            enum level-1 {
                value "1";
                description "Conditional isis level";
            }
            enum level-2 {
                value "2";
                description "Conditional isis level";
            }
        }
        description "match isis level";
    }

    grouping nexthop-attributes {
        description
            "Nexthop attributes";

        leaf nexthop {
            must 'not(contains(../exit-interface,"null0"))' {
                error-message "Nexthop cannot be configured with null0 exit-interface";
            }
            type inet:ip-address;
            description "IPv4/IPv6 nexthop address";
            reference
            '{
                "attribute-getter" : {
                "attribute" : "nexthop"
                }
            }';
        }

        leaf resolve-direct {
            type rtb-types:boolean-true;
            description "Resolve only via direct routes";
            reference
            '{
                "attribute-getter" : {
                "attribute" : "resolve_direct"
                }
            }';
        }

        leaf lookup-instance {
            type string {
                length "1..64";
	    }
            description
                "Lookup routing tables instance where the nexthop will be looked up";
            reference
            '{
                "attribute-getter" : {
                    "attribute" : "lookup_instance",
                    "expansion-getter" : {
                        "package":"static",
                        "method" : "static_instance_name_expander"
                    }
                }
            }';
        }

        leaf lookup-afi {
            type afi;
            description
                "Lookup routing tables address family where the nexthop will be looked up";
            reference
            '{
                "attribute-getter" : {
                    "attribute" : "lookup_afi"
                }
            }';
        }

        leaf lookup-safi {
            type safi;
            description
                "Lookup routing tables sub address family where the nexthop will be looked up";
            reference
            '{
                "attribute-getter" : {
                    "attribute" : "lookup_safi"
                }
            }';
        }

        leaf out-label {
            type rtb-types:mpls-label {
                range "256 .. 499968" {
                    error-message "Static out-label should be between 256 and 499968";
                }
            }
            description
                "Label to be pushed";
            reference
            '{
                "attribute-getter" : {
                    "attribute" : "out_label"
                }
            }';
        }

        leaf out-bos {
            type rtb-types:boolean-true;
            description
                "Label BOS";
            reference
            '{
                "attribute-getter" : {
                    "attribute" : "out_bos"
                }
            }';
        }

        leaf exit-interface {
            type string {
                length "1..64";
            }
            description
                "Exit interface Name";
            reference
            '{
                "attribute-getter" : {
                    "attribute" : "exit_interface",
                    "expansion-getter" : {
                        "package":"ifm",
                        "method" : "ifm_interface_logical_name_expander_custom_without_recyc_lo_ppp"
                    }
                }
            }';
        }
    }

    grouping route-attributes {
        description
            "Route attributes";

        leaf swap-label {
            type rtb-types:mpls-label;
            description
                "Label to be swapped";
            reference
            '{
                "attribute-getter" : {
                    "attribute" : "swap_label"
                }
            }';
        }

        leaf swap-bos {
            type rtb-types:boolean-true;
            description
                "Label BOS";
            reference
            '{
                "attribute-getter" : {
                    "attribute" : "swap_bos"
                }
            }';
        }

        leaf-list community {
            type rtb-types:community-type;
            description "Community associated with the route";
            reference
            '{
                "attribute-getter" : {
                    "attribute" : "community"
                }
            }';
        }

        leaf-list extended-community {
            type rtb-types:route-target-type;
            description "Extended community associated with the route";
            reference
            '{
                "attribute-getter" : {
                    "attribute" : "extended_community"
                }
            }';

        }

        leaf preference {
            type uint32;
            description
                "Numerical value signifying the priority of the route (the less, the more preferable)";
            reference
            '{
                "attribute-getter" : {
                    "attribute" : "preference"
                }
            }';
        }

        leaf route-options {
            type route-options;
            description
                "Associate various Route Options for this Route";
                reference
                '{
                    "attribute-getter" : {
                    	"attribute" : "flag"
               	     }
                }';
        }
    }

    grouping nexthop-profile-attribute {
        description
            "Nexthop profile attribute";

        leaf nexthop-profile {
            type rtb-types:string64;
            description
                "Nexthop profile name";
            reference
            '{
                "attribute-getter" : {
                    "attribute" : "nexthop_profile_name",
                    "expansion-getter" : {
                        "package":"static",
                        "method" : "static_nexthop_profile_name_expander"
                    }
                }
            }';
        }
    }

    grouping conditional-attributes {
        description
            "Conditional route related attributes";

        leaf match-instance {
            type string {
                length "1..64";
            }
            description
                "Conditional routing tables instance where the condition will be checked";
            reference
            '{
                "attribute-getter" : {
                    "attribute" : "match_instance",
                    "expansion-getter" : {
                        "package":"static",
                        "method" : "static_instance_name_expander"
                    }
                }
            }';
        }

        leaf match-afi {
            type afi;
            description
                "Conditional routing tables address family where the condition will be checked";
            reference
            '{
                "attribute-getter" : {
                    "attribute" : "match_afi"
                }
            }';
        }

        leaf match-safi {
            type safi;
            description
                "Conditional routing tables sub address family where the condition will be checked";
            reference
            '{
                "attribute-getter" : {
                    "attribute" : "match_safi"
                }
            }';
        }

        leaf compare-type {
            type compare-type;
            description
                "Conditional routing compare type";
            reference
            '{
                "attribute-getter" : {
                    "attribute" : "compare_type"
                }
            }';
        }

        leaf compare-operation {
            type compare-operation-type;
            description
                "Conditional routing compare operation";
            reference
            '{
                "attribute-getter" : {
                    "attribute" : "compare_operation"
                }
            }';
        }

        leaf compare-value {
            type uint32 {
                range "1 .. 4294967295";
            }
            description
                "Conditional routing condition value";
            reference
            '{
                "attribute-getter" : {
                    "attribute" : "compare_value"
                }
            }';
        }

        leaf match-isis-level {
            type match-isis-level-type;
            description
                "Conditional routing isis neighbor level";
            reference
            '{
                "attribute-getter" : {
                    "attribute" : "match_isis_level"
                }
            }';
        }

        leaf match-interface {
            type string {
                length "1..64";
            }
            description
                "Conditional routing interface where the bgp or isis neighbor state need to checked";
            reference
            '{
                "attribute-getter" : {
                    "attribute" : "match_interface",
                    "expansion-getter" : {
                        "package":"ifm",
                        "method" : "ifm_interface_logical_name_expander_without_recyc_lo_ppp"
                    }
                }
            }';
        }

        container match-peer {
            container ipv4 {
                description
                    "Configuration ipv4 peer related attributes";
                reference
                '{
                    "table-getter": {
                        "library": "libstaticd.so",
                        "symbol": "static_yang_get_conditional_profile_cfg_tbl_templ",
                        "type" :  "static_conditional_profile_config_table",
                        "inherit-attribute":["conditional_profile_name"]
                    }
                }';
                leaf peer-address {
                    type inet:ipv4-address-no-zone;
                    must "not(../../ipv6/peer-address)" {
                        error-message "Ipv4 and Ipv6 peers cannot be configured in same conditional profile";
                    }
                    must "../source-address" {
                        error-message "Peer address and source address is mandatory";
                    }
                    must "not(../../../match-interface)" {
                        error-message "Interface and IP addresses cannot be configured in same conditional profile";
                    }
                    description "Peer address to be matched in the BGP session";
                    reference
                    '{
                        "attribute-getter" : {
                            "attribute" : "match_peer_ipv4_address"
                        }
                    }';
                }
                leaf source-address {
                    type inet:ipv4-address-no-zone;
                    must "../peer-address" {
                        error-message "Peer address and source address is mandatory";
                    }
                    description "Source address to be matched in the BGP session";
                    reference
                    '{
                        "attribute-getter" : {
                            "attribute" : "match_source_ipv4_address"
                        }
                    }';
                }
            }
            container ipv6 {
                description
                    "Configuration ipv6 BGP peer related attributes";
                reference
                '{
                    "table-getter": {
                        "library": "libstaticd.so",
                        "symbol": "static_yang_get_conditional_profile_cfg_tbl_templ",
                        "type" :  "static_conditional_profile_config_table",
                        "inherit-attribute":["conditional_profile_name"]
                    }
                }';
                leaf peer-address {
                    type inet:ipv6-address-no-zone;
                    description "Peer address to be matched in the BGP session";
                    must "../source-address" {
                        error-message "Peer address and source address is mandatory";
                    }
                    must "not(../../../match-interface)" {
                        error-message "Interface and IP addresses cannot be configured in same conditional profile";
                    }
                    reference
                    '{
                        "attribute-getter" : {
                            "attribute" : "match_peer_ipv6_address"
                        }
                    }';
                }
                leaf source-address {
                    type inet:ipv6-address-no-zone;
                    description "Source address to be matched in the BGP session";
                    must "../peer-address" {
                        error-message "Peer address and source address is mandatory";
                    }
                    reference
                    '{
                        "attribute-getter" : {
                            "attribute" : "match_source_ipv6_address"
                        }
                    }';
                }
            }
        }
    }

    grouping conditional-profile-attribute {
        description
            "Conditional profile attribute";

        leaf-list conditional-profile {
            type rtb-types:string64;
            must "count(../conditional-profile) <= 10"{
                error-message "Maximum of 10 conditional profiles are supported";
            }
            ordered-by user;
            description "Conditional profile name";
            reference
            '{
                "attribute-getter" : {
                    "attribute" : "conditional_profile_list",
                    "expansion-getter" : {
                        "package":"static",
                        "method" : "static_conditional_profile_name_expander"
                    }
                }
            }';
        }
    }

    grouping static-top {
        description
            "This grouping define top-level static route model data";
        container static {
	        presence static;
            description
                "Configuration data for static route configuration table";

            container route {
	            presence route;
                description
                    "Configuration data for static route configuration table";

                list ipv4
                {
                    key "prefix4 safi nexthop-profile";
                    description
                        "IPv4 static route configuration commands";
                    reference
                    '{
                        "table-getter": {
                            "library": "libstaticd.so",
                            "symbol": "static_yang_get_prefix_cfg_tbl_templ",
                            "type" :  "static_prefix_config_table",
                            "inherit-attribute":["instance_name"]
                        }
                    }';

                    leaf prefix4 {
                        type inet:ipv4-prefix;
                        description
                            "IPv4 prefix address";
                        reference
                        '{
                            "attribute-getter" : {
                                "attribute" : "prefix4"
                            }
                        }';
                    }

                    leaf safi {
                        type safi;
                        description
                            "Destination routing tables sub address family";
                        reference
                        '{
                            "attribute-getter" : {
                                "attribute" : "destination_safi"
                            }
                        }';
                    }

                    uses nexthop-profile-attribute;
                    uses route-attributes;
                    uses conditional-profile-attribute;
                }

                list ipv6
                {
                    key "prefix6 safi nexthop-profile";
                    description
                        "IPv6 static route configuration commands";
                    reference
                    '{
                        "table-getter": {
                            "library": "libstaticd.so",
                            "symbol": "static_yang_get_prefix_cfg_tbl_templ",
                            "type" :  "static_prefix_config_table",
                            "inherit-attribute":["instance_name"]
                        }
                    }';

                    leaf prefix6 {
                        type inet:ipv6-prefix;
                        description
                            "IPv6 prefix address";
                        reference
                        '{
                            "attribute-getter" : {
                                "attribute" : "prefix6"
                            }
                        }';
                    }

                    leaf safi {
                        type safi;
                        description
                            "Destination routing tables sub address family";
                        reference
                        '{
                            "attribute-getter" : {
                                "attribute" : "destination_safi"
                            }
                        }';
                    }

                    uses nexthop-profile-attribute;
                    uses route-attributes;
                    uses conditional-profile-attribute;
                }

                list multicast4
                {
                    key "source group nexthop-profile";
                    description
                        "Static multicast route configuration commands";
                    reference
                    '{
                        "table-getter": {
                            "library": "libstaticd.so",
                            "symbol": "static_yang_get_prefix_cfg_tbl_templ",
                            "type" :  "static_prefix_config_table",
                            "inherit-attribute":["instance_name"]
                        }
                    }';

                    leaf source {
                        type inet:ipv4-prefix;
                        description
                            "IPv4 source address";
                        reference
                        '{
                            "attribute-getter" : {
                                "attribute" : "prefix4"
                            }
                        }';
                    }

                    leaf group {
                        type inet:ipv4-prefix;
                        description
                            "IPv4 Multicast group address";
                        reference
                        '{
                            "attribute-getter" : {
                                "attribute" : "mgroup4"
                            }
                        }';
                    }

                    uses nexthop-profile-attribute;
                    uses route-attributes;
                    uses conditional-profile-attribute;
                }

                list mpls
                {
                    key "in-label in-bos safi nexthop-profile";
                    description
                        "Static mpls route configuration commands";
                    reference
                    '{
                        "table-getter": {
                            "library": "libstaticd.so",
                            "symbol": "static_yang_get_prefix_cfg_tbl_templ",
                            "type" :  "static_prefix_config_table",
                            "inherit-attribute":["instance_name"]
                        }
                    }';

                    leaf in-label {
                        type rtb-types:mpls-label {
                            range "256 .. 499968" {
                                error-message "Static in-label should be between 256 and 499968";
                            }
                        }
                        must "count(../../../../../instance[not(name = current()/../../../../name)]/static/
                                route/mpls/in-label[. = current()]) = 0" {
                            error-message "Conflicting labels for in-label across instances";
                        }
                        must "count(../../../../../instance/protocol/bgp/address-family/srgb[base + index = current()]) = 0" {
                            error-message "Conflicting labels for in-label and BGP";
                        }
                        must "count(../../../../../instance/protocol/bgp/address-family[label = current()]) = 0" {
                            error-message "Conflicting labels for in-label and BGP unicast";
                        }
                        must "count(../../../../../instance/protocol/bgp/address-family/interface[label-base + sid-index = current()]) = 0" {
                            error-message "Conflicting labels for in-label and BGP interface";
                        }
                        description
                            "MPLS Label incoming CFG Key";
                        reference
                        '{
                            "attribute-getter" : {
                                "attribute" : "in_label"
                            }
                        }';
                    }

                    leaf in-bos {
                        type rtb-types:boolean-type;
                        description
                            "Incoming label BOS";
                        reference
                        '{
                            "attribute-getter" : {
                                "attribute" : "in_bos"
                            }
                        }';
                    }

                    leaf safi {
                        type safi;
                        description
                            "Destination routing tables sub address family";
                        reference
                        '{
                            "attribute-getter" : {
                                "attribute" : "destination_safi"
                            }
                        }';

                        must '(. != "labeled-unicast") and (. != "multicast")' {
                            error-message "MPLS labeled-unicast or multicast static routes cannot be configured";
                        }
                    }

                    uses nexthop-profile-attribute;
                    uses route-attributes;
                    uses conditional-profile-attribute;
                }
            }

            list nexthop-profile
            {
                key "name";
                  description
                      "Nexthop attributes related configuration commands";
                reference
                '{
                    "table-getter": {
                        "library": "libstaticd.so",
                        "symbol": "static_yang_get_nh_profile_cfg_tbl_templ",
                        "type" :  "static_nh_profile_config_table",
                        "inherit-attribute": ["instance_name"]
                    }
                }';

                leaf name {
                    type string {
                        length "1..64";
                    }
                    description
                        "Nexthop profile name";
                    reference
                    '{
                        "attribute-getter" : {
                            "attribute" : "nexthop_profile_name"
                        }
                    }';
                }

                uses nexthop-attributes;

            }

            list conditional-profile
            {
                key "name";
                  description
                      "Conditional route related configuration attributes";
                reference
                '{
                    "table-getter": {
                        "library": "libstaticd.so",
                        "symbol": "static_yang_get_conditional_profile_cfg_tbl_templ",
                        "type" :  "static_conditional_profile_config_table"
                    }
                }';

                leaf name {
                    type rtb-types:string64;
                    description
                        "Conditional route profile name";
                    reference
                    '{
                        "attribute-getter" : {
                            "attribute" : "conditional_profile_name"
                        }
                    }';
                }

                uses conditional-attributes;

            }

        }
    }
}
