submodule rtbrick-debuginfo {
    yang-version 1.1;
    belongs-to rtbrick-config {
        prefix config;
    }

    organization
      "Rtbrick";
    contact
      "yang-support@rtbrick.com";
    description
      "This sub-module contains the YANG structure for the debug info utility cro job configuration.
       debug-information
           +-> collector
               +-> interval
                   +-> {interval}
               +-> max-files
                   +->{max_files}
      ";
    revision 2024-02-13 {
        description "First revision";
        reference "None";
    }

    grouping debuginfo {
        description "This grouping define dui cron job data.";
        container debug-information {
            description "DUI Configuration";
            container collector {
                reference
                '{
                    "table-getter": {
                        "type" :  "debug_info_cron_config_table",
                        "table-name" : "global.debug.info.cron.config",
                        "notification-type" : "table-change",
                        "notification-interval": 500,
                        "default-attribute" : [ { "configuration_name" : "rtbrick-debug-info"}, {"interval" : "12" } ,  {"max_files" : "10" }]
                    }
                }';
                description "DUI Configuration";
                leaf interval {
                    description "DUI cron job interval in hours";
                    type  uint32 {
                        range "2..168";
                    }
                    reference
                    '{
                        "attribute-getter" : {
                            "attribute" : "interval"
                        }
                    }';
                }
                leaf  max-files {
                    description "DUI cron job max-files";
                    type uint32{
                        range "1..50";
                    }
                    reference
                    '{
                        "attribute-getter" : {
                            "attribute" : "max_files"
                        }
                    }';
                }
        }
        }
    }
    uses debuginfo;
}
