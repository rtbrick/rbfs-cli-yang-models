submodule rtbrick-fragmentation {
    yang-version 1.1;

    belongs-to rtbrick-config {
        prefix config;
    }

    import clixon-autocli{
        prefix autocli;
    }

    organization
      "Rtbrick";

    contact
      "Author : Sudhir C R (sudhir@rtbrick.com)";

    description
      "This module describes the YANG model for the fragmentation configuration.";

    revision 2022-07-01 {
        description
        "Configuration hierarchy for fragmentation";

        reference "None";
    }

    typedef fragmentation-afi {
        type enumeration {
            enum ipv4 {
                value "0";
                description "IPv4 address family";
            }
        }
        description "Fragmentation address family";
    }

    typedef state {
        type enumeration {
            enum disabled {
                value "0";
                description "Fragmentation disabled";
            }
            enum cpu {
                value "1";
                description "Software Fragmentation";
            }
        }
        description "Fragmentation state";
    }

    typedef enable-disable {
        type enumeration {
            enum disable {
                value "0";
                description "Fragmentation reinjection disabled";
            }
            enum enable {
                value "1";
                description "Fragmentation reinjection enabled";
            }
        }
        description "Fragmentation reinjection state";
    }

    grouping fragmentation-top {
        description
            "Top-level fragmentation configuration";
        container fragmentation {
            description
                "Fragmentation configuration";
            container ipv4 {
                description
                    "Fragmentation configuration for IPv4 address family";
                reference
                '{
                    "table-getter": {
                        "table-name": "global.fragmentation.config",
                        "type"    : "fragmentation_cfg_table",
                        "default-attribute" : [ { "type" : "ipv4"} ]
                    }
                }';

                leaf state {
                    type state;
                    description
                        "Fragmentation state";
                    reference
                    '{
                        "attribute-getter" : {
                            "attribute" : "state"
                        }
                    }';
                }
                leaf reinjection {
                    type enable-disable;
                    autocli:hide;
                    description
                        "Reinjection of fragmented packets";
                    reference
                    '{
                        "attribute-getter" : {
                            "attribute" : "reinjection"
                        }
                    }';
                }
                must "not(reinjection = 'enable') or state = 'cpu'" {
                    error-message "Reinjection can be enabled only if state is cpu";
                }
            }
        }
    }
}
