module rtbrick-ospf-types {
    yang-version 1.1;
    prefix rtb-ospf-types;
    namespace
    "urn:config:rtbrick:ospf:types";

    organization "rtbrick";

    contact
      "yang-support@rtbrick.com";

    description
      "This module contains general data definitions for use in OSPF YANG
    model.";

    revision "2022-03-16" {
      description "Addition of OSPF types for rtbrick";
      reference
        "0.0.1";
    }

    typedef rib-source {
        type enumeration {
            enum direct {
                value "2";
                description "Source direct";
            }
            enum static {
                value "3";
                description "Source static";
            }
            enum isis {
                value "4";
                description "Source isis";
            }
            enum bgp {
                value "5";
                description "Source bgp";
            }
            enum ppp {
                value "11";
                description "Source PPP";
            }
            enum ipoe {
                value "17";
                description "Source IPoE";
            }
        }
    }

    typedef metric-type {
         type enumeration {
            enum type-1 {
                value "1";
                description "Metric Type External Type-1";
            }
            enum type-2 {
                value "2";
                description "Metric Type External Type-2";
            }
        }
    }

    typedef protocol-metric {
        type uint32 {
            range  "1 .. 16777215";
        }
    }

    typedef enable {
        type enumeration {
            enum "enable" {
                value "1";
                description "enable";
            }
        }
        description "Data type for enable";
    }

}
