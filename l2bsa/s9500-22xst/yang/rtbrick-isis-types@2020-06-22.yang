module rtbrick-isis-types {
    yang-version 1.1;
    prefix rtb-isis-types;
    namespace
    "urn:config:rtbrick:isis:types";

    organization "rtbrick";

    contact
    "prejeeth@rtbrick.com";

    description
      "This module contains general data definitions for use in ISIS YANG
    model.";

    revision "2020-06-22" {
      description "Addition of ISIS types for rtbrick";
      reference
        "0.3.3";

    }


    typedef level-number {
      type uint8 {
        range "1..2";
      }
      description
        "This type defines ISIS level.";
    }
    

    //[a-fA-F0-9]{2}(\.[a-fA-F0-9]{4}){0,7}\/(8|24|40|104)'
    // The above regex is not accepted by the pyang validator, let us stick to string
    // and rely on BDS for validation
    typedef  iso-prefix {
      type string {
          length "1..64";
      }
      description
        "This type defines rtbrick iso prefix";
    }

    typedef net {
      type string {
        length "1..64";
        pattern
          '[a-fA-F0-9]{2}(\.[a-fA-F0-9]{4}){3,9}\.[a-fA-F0-9]{2}$';
      }
      description
        "This type defines OSI NET address. A NET should should be in
      the form xx.yyyy.yyyy.yyyy.00 with up to 9 sets of yyyy.";
    }

    typedef area-address {
      type string {
        length "1..64";
        pattern
          '[0-9A-Fa-f]{2}\.([0-9A-Fa-f]{4}\.){0,3}';
      }
      description
        "This type defines the ISIS area address.";
    }

    typedef system-id {
      type string {
        length "1..64";
        pattern
          '[0-9A-Fa-f]{4}\.[0-9A-Fa-f]{4}\.[0-9A-Fa-f]{4}';
      }
      description
        "This type defines ISIS system id using pattern, system id looks
       like : 0143.0438.AeF0";
    }

    typedef extended-circuit-id {
      type uint32;
      description
        "This type defines interface circuit ID.";
    }

    typedef lsp-id {
      type string {
        length "1..64";
        pattern
          '[0-9A-Fa-f]{4}\.[0-9A-Fa-f]{4}\.[0-9A-Fa-f]'
            + '{4}\.[0-9][0-9]-[0-9][0-9]$';
      }
      description
        "This type defines ISIS LSP ID. ISIS LSP ID type should be in
      the form of xxxx.xxxx.xxxx.xx-xx";
    }

    typedef snpa {
      type string {
        length "0 .. 20";
      }
      description
        "This type defines Subnetwork Point of Attachment format.";
    }

    typedef auth-type {
        type enumeration {
            enum clear_text {
                value "1";
                description "Clear text type";
            }
            enum md5 {
                value "2";
                description "Md5 type";
            }
            enum sha1 {
                value "3";
                description "SHA1 type";
            }
            enum sha224 {
                value "4";
                description "SHA224 type";
            }
            enum sha256 {
                value "5";
                description "SHA256 type";
            }
            enum sha384 {
                value "6";
                description "SHA384 type";
            }
            enum sha512 {
                value "7";
                description "SHA512 type";
            }
        }
        description "Authentication type";
    }

    typedef flood-filter-action {
        type enumeration {
            enum block {
                description "Block the LSPs";
            }
            enum flood {
                value "2";
                description "Flood the LSPs";
            }
        }
        description "Flooding filter actions";
    }
    typedef afi {
        type enumeration {
            enum ipv4 {
                value "0";
                description "IPv4 address";
            }
            enum ipv6 {
                value "1";
                description "IPv6 address";
            }
        }
        description "Afi data type";
    }

    typedef safi {
        type enumeration {
            enum labeled-unicast {
                value "0";
                description "Labeled unicast";
            }
            enum multicast {
                value "1";
                description "Labeled multicast";
            }
            enum unicast {
                value "2";
                description "Unicast";
            }
        }
        description "Safi data type";

    }

    typedef isis-interface {
        type enumeration {
            enum point-to-point {
                value "1";
                description "P2P";
            }
            enum broadcast {
                value "2";
                description "LAN";
            }
        }
        description "ISIS interface type";
    }

    typedef protocol-metric {
        type uint32 {
            range  "0 .. 16777215";
        }
    }

    typedef rib-source {
        type enumeration {
            enum direct {
                value "2";
                description "Source direct";
            }
            enum static {
                value "3";
                description "Source static";
            }
            enum ospf {
                value "5";
                description "Source OSPF";
            }
            enum bgp {
                value "7";
                description "Source BGP";
            }
            enum ppp {
                value "11";
                description "Source PPP";
            }
            enum ipoe {
                value "17";
                description "Source IPoE";
            }
        }
        description "ISIS interface type";
    }

    // From rib_source_sub_type_map@libprotocolinfra
    typedef destination-subtype {
        type enumeration {
            enum level-1 {
                value "31";
                description "Source ISIS level-1";
            }
            enum level-2 {
                value "32";
                description "Source ISIS level-2";
            }
        }
        description "ISIS interface type";
    }
}  // module rtbrick-isis-types
