submodule rtbrick-link-aggregation {
    yang-version 1.1;

    belongs-to rtbrick-config {
       prefix config;
    }

    import rtbrick-types {
        prefix "rtb-types";
    }

    include rtbrick-interface;
    include rtbrick-l2x;

    organization
      "Rtbrick";

    contact
      "yang-support@rtbrick.com";

    description
        "This module contains the YANG structure for the link-aggregation module
        +-> {link-aggregation}
            +-> {interface}
            +-> {mode}
            +-> {minimum-link-count}
            +-> {member-interface-name}
                +-> {lacp-mode}
                +-> {lacp-timeout}";

    revision 2021-04-27 {
        description "First revision";
        reference "None";
    }

    typedef up-down {
        type enumeration {
            enum "down" {
                value 0;
                description "Not ready to pass packets";
            }
            enum "up" {
                value 1;
                description "Ready to pass packets";
            }
        }
        description "Up/down data type";
    }

    typedef lag-mode {
        type enumeration {
            enum "static" {
                value 0;
                description "Link-aggregation interface will work in static mode";
            }
            enum "lacp" {
                value 1;
                description "Link-aggregation interface will work in lacp mode";
            }
        }
        description "Link-aggregation mode data type";
    }


    typedef lacp-mode {
        type enumeration {
            enum "active" {
                value 0;
                description "Interface is an active member";
            }
            enum "passive" {
                value 1;
                description "Interface is a passive member";
            }
        }
        description "Indicates member-interface is active or passive";
    }

    typedef lacp-timeout {
        type enumeration {
            enum "long" {
                value 0;
                description
                    "Member-interface with long timeout wishes to use long timeouts
                    to detect status of the aggregate, i.e., will expect
                    less frequent transmissions. Long timeout is 90 seconds";
            }
            enum "short" {
                value 1;
                description
                    "Member-interface with SHOR timeout wishes to use short timeouts,
                    i.e., expects frequent transmissions to detect status changes.
                    Short timeout is 3 seconds";
            }
        }
        description "The timeout type (short or long) used by the Member-interface";
    }


    grouping link-aggregation-top {

        container link-aggregation {
            description "Link aggregation configuration";
            reference
            '{
                "table-getter": {
                    "table-name" : "global.lag.config",
                    "type"    : "lag_global_config_table",
                    "default-attribute" : [ { "mode" : "global" } ]
                }
            }';

            list interface {
                key "interface-name";
                description "LACP interface configuration";
                reference
                '{
                    "table-getter": {
                        "table-name" : "global.interface.lag.config",
                        "type"    : "lag_interface_config_table"
                    }
                }';
                leaf interface-name {
                    type rtb-types:lag-interface-type;
                    description "Link aggregation interface name";
                    reference
                    '{
                        "attribute-getter" : {
                            "attribute" : "lag_interface_name"
                        }
                    }';
                }
               leaf description {
                    type rtb-types:string128;
                    description "Link aggregation interface description";
                    reference
                    '{
                        "attribute-getter" : {
                            "attribute" : "description"
                        }
                    }';
                }
                leaf mode
                {
                    type lag-mode;
                    description "Mode of the link aggregation interface, static or lacp. [Default mode: lacp]";
                    reference
                    '{
                        "attribute-getter" : {
                            "attribute" : "mode"
                        }
                    }';
                }

                leaf minimum-link-count {
                    type uint16;
                    description "Minimum number of active member links required for the link aggregation interface. [Default value: 1]";
                    reference
                    '{
                        "attribute-getter" : {
                            "attribute" : "minimum_link_count"
                        }
                    }';
                }

                leaf redundancy-session-id {
                    type uint16 {
                        range "1..65535";
                    }
                    description "The value for the redundancy group session id";
                    reference
                    '{
                        "attribute-getter" : {
                            "attribute" : "rd_session_id"
                        }
                    }';
                    must "not(../../interface[redundancy-session-id = current()]/interface-name != current()/../interface-name)" {
                        error-message "Redundancy session ID must be unique across all interfaces.";
                    }
                }

                leaf system-id {
                    type rtb-types:rtb-unicast-mac-type;
                    description
                        "Redundancy System ID of link-aggregation interface";
                    reference
                    '{
                        "attribute-getter" : {
                            "attribute" : "rd_system_id"
                        }
                    }';
                }

                list member-interface {
                    key "member-interface-name";
                    description "Link aggregation member interface configuration";
                    reference
                    '{
                        "table-getter": {
                            "table-name" : "global.interface.lag.member.config",
                            "type"    : "lag_member_interface_config_table",
                            "inherit-attribute" : [ "lag_interface_name" ]
                        }
                    }';

                    leaf member-interface-name {
                        type rtb-types:lag-member-interface-type;
                        description "Link aggregation member interface name";
                        must 'count(../../../../interface[name=current()]/unit) = 0' {
                            error-message "Lag member interface cannot have any logical interface configured";
                        }
                        must 'count(../../../../interface[name=current()]/mru) = 0' {
                            error-message "Lag member interface cannot have mru configured";
                        }
                        must 'count(../../../../interface[name=current()]/auto-negotiation) = 0' {
                            error-message "Lag member interface cannot have auto-negotiation configured";
                        }
                        must 'count(../../../../interface[name=current()]/class-of-service) = 0' {
                            error-message "Lag member interface cannot have class-of-service configured";
                        }
                        must 'count(../../../../l2x/name[incoming-interface=current()]) = 0' {
                            error-message "Lag member interface cannot have L2X configured";
                        }
                        must 'count(../../../../l2x/name[outgoing-interface=current()]) = 0' {
                            error-message "Lag member interface cannot have L2X configured";
                        }
                        must 'count(../../../../link-aggregation/interface/member-interface[member-interface-name=current()]) = 1' {
                                error-message "Member interface name has to be unique across all lags";
                        }
                        must 'count(../../../../forwarding-options/mirror/source[interface = current()])=0' {
                            error-message "Mirror configurations are restricted on lag member interfaces";
                        }
                        must 'count(../../../../interface[name=current()]/breakout/map) = 0' {
                            error-message "Lag member interface cannot have breakout mode configured";
                        }
                        reference
                        '{
                            "attribute-getter" : {
                                "attribute" : "member_interface_name",
                                "expansion-getter" : {
                                    "package":"ifm",
                                    "method" :"ifm_lag_member_interface_name_expander"
                                }
                            }
                        }';
                    }
                    leaf lacp-mode
                    {
                        type lacp-mode;
                        description "Indicates member-interface is active or passive. [Default value: active]";
                        reference
                        '{
                            "attribute-getter" : {
                                "attribute" : "lacp_member_mode"
                            }
                        }';
                    }
                    leaf lacp-timeout
                    {
                        type lacp-timeout;
                        description "The timeout type (short or long) used by the member-interface. [Default value: short]";
                        reference
                        '{
                            "attribute-getter" : {
                                "attribute" : "timeout"
                            }
                        }';
                    }

                    leaf port-priority {
                        type uint16 {
                            range "1..65535";
                        }
                        description "The value for the port priority range. The lower the value, the higher the port priority. [Default value: 255]";
                        reference
                        '{
                            "attribute-getter" : {
                                "attribute" : "port_priority"
                            }
                        }';
                    }

                }
            }

        }
    }
    uses link-aggregation-top;
}
