submodule rtbrick-access {
    yang-version 1.1;
    belongs-to rtbrick-config {
        prefix config;
    }

    organization
      "Rtbrick";
    contact
      "Authors: Navaneeth Y V (navaneethyv@rtbrick.com)";

    description
        "This sub module contains the top level configurations of dummy access config to help rtbrick roles.
  	This must be pre-date the older package";

    revision 2020-01-01 {
        description
          "Dummy access yang file";
    }

    grouping access-top  {
        description "Dummy global access top level config";
    }
}
