module rtbrick-bgp-types {
    yang-version 1.1;
    namespace
    "urn:config:rtbrick:bgp:types";
    prefix rtb-bgp-types;

    organization
        "RtBrick";

    contact
      "yang-support@rtbrick.com";

    description
      "This module contains general data definitions for use in BGP YANG
    model.";

    revision "2020-08-13" {
      description "Addition of BGP types for rtbrick";
      reference
        "None";
    }

    typedef export-filter {
        type enumeration {
            enum site-id {
                value "0";
                description "site-id based filter";
            }
        }
        description "export-filter data type";
    }

    typedef l2-control-flags {
        type enumeration {
            enum enable {
                value "4";
                description "set control word";
            }
        }
        description "export-filter data type";
    }

    typedef afi {
        type enumeration {
            enum ipv4 {
                value "0";
                description "IPv4 address";
            }
            enum ipv6 {
                value "1";
                description "IPv6 address";
            }
            enum l2vpn {
                value "2";
                description "L2VPN address";
            }
        }
        description "Afi data type";
    }

    typedef safi {
        type enumeration {
            enum labeled-unicast {
                value "0";
                description "Labeled unicast";
            }
            enum multicast {
                value "1";
                description "Multicast";
            }
            enum unicast {
                value "2";
                description "Unicast";
            }
            enum vpn-multicast {
                value "3";
                description "VPN multicast";
            }
            enum vpn-unicast {
                value "4";
                description "VPN unicast";
            }
            enum evpn {
                value "5";
                description "Ethernet VPN";
            }
            enum evpn-vpws {
                value "6";
                description "Virtual private wire service ";
            }
            enum vpls-vpws {
                value "7";
                description "vpls-vpws VPN";
            }
            enum vpls {
                value "8";
                description "EVPN vpls-vpws VPN";
            }
            enum flowspec {
                value "9";
                description "flow specification";
            }
        }
        description "Safi data type";
    }

    typedef resolve-safi {
        type enumeration {
            enum labeled-unicast {
                value "0";
                description "Labeled unicast";
            }
            enum unicast {
                value "1";
                description "Unicast";
            }
        }
        description "Resolve NH Safi data type";
    }

    typedef pg-safi {
        type enumeration {
            enum labeled-unicast {
                value "0";
                description "Labeled unicast";
            }
            enum unicast {
                value "1";
                description "Unicast";
            }
            enum vpn-multicast {
                value "2";
                description "VPN multicast";
            }
            enum vpn-unicast {
                value "3";
                description "VPN unicast";
            }
            enum evpn {
                value "4";
                description "Ethernet VPN";
            }
            enum evpn-vpws {
                value "5";
                description "Virtual private wire service ";
            }
            enum vpls-vpws {
                value "6";
                description "vpls-vpws VPN";
            }
            enum vpls {
                value "7";
                description "EVPN vpls-vpws VPN";
            }
            enum flowspec {
                value "8";
                description "flow specification";
            }
        }
        description "Peer Group Safi data type";
    }

    typedef enable-disable {
        type enumeration {
            enum disable {
                value "0";
                description "Disable the configuration";
            }
            enum enable {
                value "1";
                description "Enable the configuration";
            }
        }
        description "Enable and disable common type";
    }

    typedef add-path-opt {
        type enumeration {
            enum receive-only {
                value "1";
                description "Receive additional paths";
            }
            enum send-only {
                value "2";
                description "Send additional paths";
            }
            enum both {
                value "3";
                description "Send and receive additional paths";
            }
        }
        description "BGP Add-Path options";
    }

    typedef rib-source {
        type enumeration {
            enum direct {
                value "2";
                description "Directly connected routes";
            }
            enum static {
                value "3";
                description "Static routes";
            }
            enum isis {
                value "4";
                description "ISIS routes";
            }
            enum ospf {
                value "5";
                description "OSPF routes";
            }
            enum pim {
                value "9";
                description "pim routes";
            }
            enum igmp {
                value "10";
                description "IGMP routes";
            }
            enum ppp {
                value "11";
                description "ppp routes";
            }
            enum arp-nd {
                value "15";
                description "arp-nd routes";
            }
            enum ipoe {
                value "17";
                description "ipoe routes";
            }
            enum nat {
                value "22";
                description "nat routes";
            }
        }
        description "RIB source type";
    }

    typedef subtype-isis {
        type enumeration {
            enum level-1 {
                value "31";
                description "level-1 routes";
            }
            enum level-2 {
                value "32";
                description "level-2 routes";
            }
        }
        description "ISIS sub-type";
    }

    typedef subtype-ospf {
        type enumeration {
            enum intra-area {
                value "23";
                description "intra area routes";
            }
            enum inter-area {
                value "24";
                description "inter area routes";
            }
            enum external-type-1 {
                value "25";
                description "external routes type-1";
            }
            enum external-type-2 {
                value "26";
                description "external routes type-2";
            }
            enum nssa-external-type-1 {
                value "27";
                description "nssa external routes type1";
            }
            enum nssa-external-type-2 {
                value "28";
                description "nssa external routes type-2";
            }
        }
        description "ISIS sub-type";
    }

    typedef tos-precedence {
        type enumeration {
            enum routine {
                value "0";
                description "Precedence type routine";
            }
            enum priority {
                value "32";
                description "Precedence type priority";
            }
            enum immediate {
                value "64";
                description "Precedence type immediate";
            }
            enum flash {
                value "96";
                description "Precedence type flash";
            }
            enum flash-override {
                value "128";
                description "Precedence type flash-override";
            }
            enum critics {
                value "160";
                description "Precedence type critics";
            }
            enum internetwork-control {
                value "192";
                description "Precedence type internetwork-control";
            }
            enum network-control {
                value "224";
                description "Precedence type network-control";
            }
        }
        description "Type of service (ToS) delay type";
    }

    typedef tos-delay {
        type enumeration {
            enum normal {
                value "0";
                description "Normal delay";
            }
            enum low {
                value "16";
                description "Low delay";
            }
        }
        description "Type of service (ToS) delay type";
    }

    typedef tos-throughput {
        type enumeration {
            enum normal {
                value "0";
                description "Normal throughput";
            }
            enum high {
                value "8";
                description "High throughput";
            }
        }
        description "Type of service (ToS) throughput type";
    }

    typedef tos-reliability {
        type enumeration {
            enum normal {
                value "0";
                description "Normal reliability";
            }
            enum high {
                value "4";
                description "High reliability";
            }
        }
        description "Type of service (ToS) reliability type";
    }

    typedef tos-cost {
        type enumeration {
            enum normal {
                value "0";
                description "Normal cost";
            }
            enum low {
                value "2";
                description "Low cost";
            }
        }
        description "Type of service (ToS) cost type";
    }

    typedef protocol-pref {
        type uint32 {
            range "1..255";
        }
        description "Protocol preference";
    }

    typedef val-filter {
        type enumeration {
            enum disable {
                value "0";
                description "Validation disable";
            }
            enum mark-only {
                value "1";
                description "Mark RPKI state in route. Validation disable";
            }
            enum loose {
                value "2";
                description "Loose validation";
            }
            enum strict {
                value "3";
                description "Strict validation";
            }
        }
        description "Validation Filters";
    }

    typedef bgp-ignore {
        type enumeration {
            enum ignore {
                value "1";
                description "Ignore the configuration";
            }
        }
        description "Ignore common type";
    }
}
