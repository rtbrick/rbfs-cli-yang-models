submodule rtbrick-oam {
    yang-version 1.1;
    belongs-to rtbrick-config {
        prefix config;
    }

    import ietf-inet-types {
        prefix "inet";
    }

    organization "RtBrick";

    revision "2025-04-22" {
        description
            "First revision of OAM configuration";
        reference
            "None";
    }
    typedef cfm_interval_type {
        type enumeration {
            enum 100ms {
                value 3;
            }
            enum 1s {
                value 4;
            }
            enum 10s {
                value 5;
            }
        }
    }
    typedef short_name_format {
        type enumeration {
            enum character-string {
                value 1;
            }
            enum primary-vid {
                value 2;
            }
            enum icc-based {
                value 3;
            }
        }
    }
    container oam {
        description "Operation Administration and Maintenance configuration hierarchy";
        container cfm {
            description "Connectivity Fault Management configuration hierarchy ";
            list session {
                key "name";
                unique "maintenance-association local-mep remote-mep interface";
                description "Session name";
                reference
                '{
                    "table-getter": {
                        "table-name": "global.oam.cfm.session.config",
                        "type" :  "oam_cfm_session_config_table"
                    }
                }';
                leaf name {
                    type string {
                        length "1..48";
                    }
                    description "Unique name for the OAM CFM session";
                    reference
                    '{
                        "attribute-getter" : {
                            "attribute" : "session"
                        }
                    }';   
                }

                leaf level {
                    type uint8 {
                        range "0..7";
                    }
                    description "CFM level";
                    reference
                    '{
                        "attribute-getter" : {
                            "attribute" : "level"
                        }
                    }';   
                }
                leaf maintenance-domain {
                    type string {
                        length "1..48";
                    }
                    description "Maintenance domain name";
                    reference
                    '{
                        "attribute-getter" : {
                            "attribute" : "maintenance_domain"
                        }
                    }';
                } 
                leaf maintenance-association {
                    type string {
                        length "1..48";
                    }
                    description "Maintenance association name";
                    reference
                    '{
                        "attribute-getter" : {
                            "attribute" : "maintenance_association"
                        }
                    }';
                }
                leaf continuity-check-interval {
                    type cfm_interval_type;
                    description "Continuity check interval";
                    reference
                    '{
                        "attribute-getter" : {
                            "attribute" : "continuity_check_interval"
                        }
                    }';
                }
                leaf local-mep {
                    type uint16 {
                        range "1..8191";
                    }
                    description "Local end-point identifier";
                    reference
                    '{
                        "attribute-getter" : {
                            "attribute" : "local_endpoint_id"
                        }
                    }';
                }
                leaf remote-mep {
                    type uint16 {
                        range "1..8191";
                    }
                    description "Remote end-point identifier";
                    reference
                    '{
                        "attribute-getter" : {
                            "attribute" : "remote_endpoint_id"
                        }
                    }';
                    must ". != ../local-mep" {
                        error-message "Local MEP must be different from remote MEP.";
                    }
                }
                leaf interface {
                    type string {
                        length "1..64";
                    }
                    description "Logical interface name";
                    reference
                    '{
                        "attribute-getter" : {
                            "attribute" : "ifl_name",
                            "expansion-getter" : {
                                "package":"ifm",
                                "method" : "ifm_interface_logical_name_expander_without_recyc_lo_ppp"
                            }
                        }
                    }';
                }
                must level {
                    error-message "CFM level name must be configured.";
                }
                must maintenance-domain {
                    error-message "CFM maintenance-domain name must be configured.";
                }
                must maintenance-association {
                    error-message "CFM maintenance-association name must be configured.";
                }
                must local-mep {
                    error-message "CFM local-mep name must be configured.";
                }
                must remote-mep {
                    error-message "CFM remote-mep name must be configured.";
                }
                must interface {
                    error-message "CFM interface name must be configured.";
                }
            }
        }
        container bfd {
            description "Bidirectional Forwarding Detection configuration hierarchy ";
            list session {
                key "name";
                description "Session name";
                reference
                '{
                    "table-getter": {
                        "table-name": "global.oam.bfd.session.config",
                        "type" :  "oam_bfd_session_config_table"
                    }
                }';
                leaf name {
                    type string {
                        length "1..48";
                    }
                    description "Unique name for the OAM BFD session";
                    reference
                    '{
                        "attribute-getter" : {
                            "attribute" : "session_name"
                        }
                    }';
                }
                leaf peer-v4-address {
                    type inet:ipv4-address-no-zone;
                    description "Peer v4 address to be used in the BFD session";
                    reference
                    '{
                        "attribute-getter" : {
                            "attribute" : "peer_ipv4_address"
                        }
                    }';
                    must "not(../../session[peer-v4-address = current()][not(name = current()/../name)])" {
                        error-message "Multiple sessions with same IPv4 peer address are not allowed.";
                    }
                }
                leaf peer-v6-address {
                    type inet:ipv6-address-no-zone;
                    description "Peer v6 address to be used in the BFD session";
                    reference
                    '{
                        "attribute-getter" : {
                            "attribute" : "peer_ipv6_address"
                        }
                    }';
                    must "not(../../session[peer-v6-address = current()][not(name = current()/../name)])" {
                        error-message "Multiple sessions with same IPv6 peer address are not allowed.";
                    }
                }
                leaf local-v4-address {
                    type inet:ipv4-address-no-zone;
                    description "Local v4 address to be used in the BFD session";
                    reference
                    '{
                        "attribute-getter" : {
                            "attribute" : "local_ipv4_address"
                        }
                    }';
                }
                leaf local-v6-address {
                    type inet:ipv6-address-no-zone;
                    description "Local v6 address to be used in the BFD session";
                    reference
                    '{
                        "attribute-getter" : {
                            "attribute" : "local_ipv6_address"
                        }
                    }';
                }
                leaf transmit-interval {
                    type uint32 {
                        range "100..10000";
                    }
                    description "Configure transmit interval in milliseconds, default: 1000";
                    reference
                    '{
                        "attribute-getter" : {
                            "attribute" : "minimum_tx_interval"
                        }
                    }';
                }
                leaf receive-interval {
                    type uint32 {
                        range "100..10000";
                    }

                    description "Configure receive interval in milliseconds, default: 1000";
                    reference
                    '{
                        "attribute-getter" : {
                            "attribute" : "minimum_rx_interval"
                        }
                    }';
                }
                leaf detect-multiplier {
                    type uint8 {
                        range "2..255";
                    }
                    description "Configure detection multiplier, default: 3";
                    reference
                    '{
                        "attribute-getter" : {
                            "attribute" : "detect_multiplier"
                        }
                    }';
                }
                leaf interface {
                    type string {
                        length "1..64";
                    }
                    description "Logical interface name";
                    reference
                    '{
                        "attribute-getter" : {
                            "attribute" : "ifl_name",
                            "expansion-getter" : {
                                "package":"ifm",
                                "method" : "ifm_interface_logical_name_expander_without_recyc_lo_ppp"
                            }
                        }
                    }';
                }
                must "peer-v4-address or peer-v6-address" {
                    error-message "BFD session peer address must be configured.";
                }
                must "(peer-v4-address and not(peer-v6-address)) or (peer-v6-address and not(peer-v4-address))" {
                    error-message
                    "IPv4 peer address and IPv6 peer address should not be configured under same session.";
                }
                must "not(peer-v4-address) or local-v4-address" {
                    error-message
                    "When IPv4 peer address is configured, IPv4 local address must also be configured.";
                }
                must "not(peer-v6-address) or local-v6-address" {
                    error-message
                    "When IPv6 peer address is configured, IPv6 local address must also be configured.";
                }
                must interface {
                    error-message "BFD interface name must be configured.";
                }
            }
            list profile {
                key "name";
                description "Profile name";
                reference
                '{
                    "table-getter": {
                        "table-name": "global.oam.bfd.profile.config",
                        "type" :  "oam_bfd_profile_config_table"
                    }
                }';
                leaf name {
                    type string {
                        length "1..48";
                    }
                    description "Unique name for the OAM BFD profile";
                    reference
                    '{
                        "attribute-getter" : {
                            "attribute" : "profile_name"
                        }
                    }';
                }
                leaf transmit-interval {
                    type uint32 {
                        range "100..10000";
                    }
                    description "Configure transmit interval in milliseconds, default: 1000";
                    reference
                    '{
                        "attribute-getter" : {
                            "attribute" : "minimum_tx_interval"
                        }
                    }';
                }
                leaf receive-interval {
                    type uint32 {
                        range "100..10000";
                    }

                    description "Configure receive interval in milliseconds, default: 1000";
                    reference
                    '{
                        "attribute-getter" : {
                            "attribute" : "minimum_rx_interval"
                        }
                    }';
                }
                leaf detect-multiplier {
                    type uint8 {
                        range "2..255";
                    }
                    description "Configure detection multiplier, default: 3";
                    reference
                    '{
                        "attribute-getter" : {
                            "attribute" : "detect_multiplier"
                        }
                    }';
                }
            }
        }
    }
}
