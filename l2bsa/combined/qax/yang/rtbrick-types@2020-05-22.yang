module rtbrick-types {
    yang-version 1.1;
    namespace "urn:types:rtbrick";
    prefix types;
    import ietf-inet-types {
        prefix "inet";
    }
    organization
      "Rtbrick";
    contact
      "Authors: Ankit Kumar Sinha (ankit@rtbrick.com)
                 Navaneeth Y V (navaneethyv@rtbrick.com)";
    description
      "This is the type file containing the common types across rtbrick.
      Shall be included in other yangs and used in appropriate places";

    revision 2020-05-22 {
        description
          "This is the first revision of rtbrick yang file
          This file defines root module of Rtbrick,
          Applications need to add their submodule here with include statement";
        reference "None";
    }

    /* Typedef defination */
    typedef time-zone-type {
        type enumeration {
            enum GMT {
                value "0";
                description "Type GMT";
            }
            enum Local {
                value "1";
                description "Type Local";
            }
        }
        description "Time type format";
    }

    typedef boolean-type {
        type enumeration {
            enum false {
                value "0";
                description "False";
            }
            enum true {
                value "1";
                description "True";
            }
        }
        description "Boolean data type";
    }

    typedef boolean-true {
        type enumeration {
            enum true {
                value "1";
                description "True";
            }
        }
        description "Boolean data type - True";
    }

    typedef enable-disable-type {
        type enumeration {
            enum disable {
                value "0";
                description "Enable";
            }
            enum enable {
                value "1";
                description "Disable";
            }
        }
        description "Boolean enable or disable type";
    }

    typedef on-off-type {
        type enumeration {
            enum off {
                value "0";
                description "Turn on";
            }
            enum on {
                value "1";
                description "Turn off";
            }
        }
        description "Boolean on or off type";
    }

    typedef element-role-type {
        type enumeration {
            enum ACCESSLEAF {
                value "0";
                description "accessleaf";
            }
            enum BORDERLEAF {
                value "1";
                description "borderleaf";

            }
            enum SPINE {
                value "2";
                description "spine";
            }
            enum UNKNOWN {
                value "3";
                description "spine";
            }
        }
        description "Rtbrick element roles";
    }


    typedef afi {
        type enumeration {
            enum ipv4 {
                value "0";
                description "IPv4 address";
            }
            enum ipv6 {
                value "1";
                description "IPv6 address";
            }
            enum mpls {
                value "2";
                description "MPLS";
            }
        }
        description "AFI data type";
    }

    typedef safi {
        type enumeration {
            enum labeled-unicast {
                value "0";
                description "Labeled unicast";
            }
            enum multicast {
                value "1";
                description "Multicast";
            }
            enum unicast {
                value "2";
                description "Unicast";
            }
        }
        description "SAFI data type";
    }

    typedef secret-string-type {
        type string {
            pattern '$(2|5|6).+';
            length "4..512";
        }
    }

    typedef policy-name-type {
        type string {
            length "1..64";
        }
        description "Policy name";
    }

    typedef route-distinguisher-type {
        type union {
            type string {
                pattern
                    '(6553[0-5]|655[0-2][0-9]|65[0-4][0-9]{2}|6[0-4][0-9]{3}|'
                    + '[1-5][0-9]{4}|[1-9][0-9]{1,3}|[0-9]):'
                    + '(429496729[0-5]|42949672[0-8][0-9]|4294967[0-1][0-9]{2}|'
                    + '429496[0-6][0-9]{3}|42949[0-5][0-9]{4}|4294[0-8][0-9]{5}|'
                    + '429[0-3][0-9]{6}|42[0-8][0-9]{7}|4[0-1][0-9]{8}|'
                    + '[1-3][0-9]{9}|[1-9][0-9]{1,8}|[0-9])';
            }
            type string {
                pattern
                    '([1-9]|[1-9][0-9]|1[0-1][0-9]|12[0-6]|12[8-9]|'
                    + '1[3-9][0-9]|2[0-1][0-9]|22[0-3])(\.([0-9]|'
                    + '[1-9][0-9]|1[0-9][0-9]|2[0-4][0-9]|25[0-5])){3}:'
                    + '(6553[0-5]|655[0-2][0-9]|65[0-4][0-9]{2}|6[0-4][0-9]{3}|'
                    + '[1-5][0-9]{4}|[1-9][0-9]{1,3}|[0-9])';
            }
            type string {
                pattern
                    '(429496729[0-5]|42949672[0-8][0-9]|4294967[0-1][0-9]{2}|'
                    + '429496[0-6][0-9]{3}|42949[0-5][0-9]{4}|4294[0-8][0-9]{5}|'
                    + '429[0-3][0-9]{6}|42[0-8][0-9]{7}|4[0-1][0-9]{8}|'
                    + '[1-3][0-9]{9}|[1-9][0-9]{1,8}|[0-9])L:'
                    + '(6553[0-5]|655[0-2][0-9]|65[0-4][0-9]{2}|6[0-4][0-9]{3}|'
                    + '[1-5][0-9]{4}|[1-9][0-9]{1,3}|[0-9])';
            }
        }
        description "A route distinguisher value";
    }

    typedef community-type {
        type string {
            pattern
                '((6553[0-5]|655[0-2][0-9]|65[0-4][0-9]{2}|6[0-4][0-9]{3}|'
                + '[1-5][0-9]{4}|[1-9][0-9]{1,3}|[0-9]):'
                + '(6553[0-5]|655[0-2][0-9]|65[0-4][0-9]{2}|6[0-4][0-9]{3}|'
                + '[1-5][0-9]{4}|[1-9][0-9]{1,3}|[0-9]))|'
                + 'NO_EXPORT|NO_ADVERTISE|NO_EXPORT_SUBCONFED|NOPEER';
        }
    }
    typedef route-target-type {
        type union {
            type string {
                pattern
                    'target:(6553[0-5]|655[0-2][0-9]|65[0-4][0-9]{2}|6[0-4][0-9]{3}|'
                    + '[1-5][0-9]{4}|[1-9][0-9]{1,3}|[1-9]):'
                    + '(429496729[0-5]|42949672[0-8][0-9]|4294967[0-1][0-9]{2}|'
                    + '429496[0-6][0-9]{3}|42949[0-5][0-9]{4}|4294[0-8][0-9]{5}|'
                    + '429[0-3][0-9]{6}|42[0-8][0-9]{7}|4[0-1][0-9]{8}|'
                    + '[1-3][0-9]{9}|[1-9][0-9]{1,8}|[0-9])';
            }
            type string {
                pattern
                    'target:([1-9]|[1-9][0-9]|1[0-1][0-9]|12[0-6]|12[8-9]|'
                    + '1[3-9][0-9]|2[0-1][0-9]|22[0-3])(\.([0-9]|'
                    + '[1-9][0-9]|1[0-9][0-9]|2[0-4][0-9]|25[0-5])){3}:'
                    + '(6553[0-5]|655[0-2][0-9]|65[0-4][0-9]{2}|6[0-4][0-9]{3}|'
                    + '[1-5][0-9]{4}|[1-9][0-9]{1,3}|[0-9])';
            }
            type string {
                pattern
                    'target:(429496729[0-5]|42949672[0-8][0-9]|4294967[0-1][0-9]{2}|'
                    + '429496[0-6][0-9]{3}|42949[0-5][0-9]{4}|4294[0-8][0-9]{5}|'
                    + '429[0-3][0-9]{6}|42[0-8][0-9]{7}|4[0-1][0-9]{8}|'
                    + '[1-3][0-9]{9}|[1-9][0-9]{1,8}|[1-9])L:'
                    + '(6553[0-5]|655[0-2][0-9]|65[0-4][0-9]{2}|6[0-4][0-9]{3}|'
                    + '[1-5][0-9]{4}|[1-9][0-9]{1,3}|[0-9])';
            }
        }
        description "A route target value";
    }

    typedef router-id-type {
      type string {
        pattern
          '([1-9]|[1-9][0-9]|1[0-1][0-9]|12[0-6]|12[8-9]|'
            + '1[3-9][0-9]|2[0-1][0-9]|22[0-3])(\.([0-9]|'
            + '[1-9][0-9]|1[0-9][0-9]|2[0-4][0-9]|25[0-5])){3}';
      }
      description
        "An IPv4 router id in dotted quad notation";
    }

    typedef non-reserved-ipv4-address {
        type string {
            pattern
                '([1-9]|[1-9][0-9]|1[0-1][0-9]|12[0-6]|12[8-9]|'
                + '1[3-9][0-9]|2[0-1][0-9]|22[0-3])(\.([0-9]|'
                + '[1-9][0-9]|1[0-9][0-9]|2[0-4][0-9]|25[0-5])){3}';
        }
        description
            "An IPv4 address excluding some reserved prefix in dotted quad notation";
    }

    typedef non-reserved-ipv4-prefix {
        type string {
            pattern
                '([1-9]|[1-9][0-9]|1[0-1][0-9]|12[0-6]|12[8-9]|'
                + '1[3-9][0-9]|2[0-1][0-9]|22[0-3])(\.([0-9]|'
                + '[1-9][0-9]|1[0-9][0-9]|2[0-4][0-9]|25[0-5])){3}'
                + '/(([0-9])|([1-2][0-9])|(3[0-2]))';
        }
        description
            "An IPv4 prefix excluding all reserved prefix in dotted quad notation";
    }

    typedef non-reserved-ipv6-prefix-for-match {
        type inet:ipv6-prefix {
            pattern '([^fF]{2}[0-9a-fA-F]{2}|[fF][^fF][0-9a-fA-F]{2}|[^fF][fF][0-9a-fA-F]{2}|[0-9a-fA-F]{0,3}|:):.+';
            pattern '^(([^0fF].*|0[^0fF].*|0{2}[^0fF].*|0{3}[^fF].*|0{0,2}[fF][^:].+|'
                  + '(0{0,3}[fF]:(0{0,4}:){0,6}|0{0,3}[fF]:(0{0,4}:){0,6}'
                  + '([^0fF:].*|0[^0fF:].*|0{2}[^0fF:].*|0{3}[^fF:].*|0{0,2}[fF].+|0{1,4})))/(128)|'
                  + '.*/(([0-9])|([0-9]{2})|(1[0-1][0-9])|(12[0-7])))$';
            pattern '^(([^0].*|[0]{1,3}[^:0].*|(0{0,4}:){1,7}([^01:].*|0{1,3}[^01:].*|0{1,3}1[0-9a-fA-F]{0,2}:.*|1.+'
                  + '|:(0{0,3}[^01]|[^01].*|0[^01].+|00[^0].+|01.+|1.+)))/128'
                  + '|.*/(([0-9])|([0-9]{2})|(1[0-1][0-9])|(12[0-7])))$';
        }
        description
            "An IPv6 prefix excluding all reserved prefix except 'fe80::xx'";
    }

    typedef non-reserved-ipv6-prefix {
        type non-reserved-ipv6-prefix-for-match {
            pattern '([^fF][0-9a-fA-F]{3}|[fF][^eE][0-9a-fA-F]{2}|[fF][eE][^8][0-9a-fA-F]|[fF][eE][8][^0]|[0-9a-fA-F]{0,3}|:):.+';
        }
        description
            "An IPv6 prefix excluding all reserved prefix";
    }

    typedef non-reserved-ipv6-address-no-zone {
        type types:non-reserved-ipv6-address {
            pattern '[0-9a-fA-F:\.]*';
        }
        description
            "An IPv6 address without zone index excluding all reserved address";
    }

    typedef non-reserved-ipv6-address {
        type inet:ipv6-address {
            pattern '([^fF]{2}[0-9a-fA-F]{2}|[fF][^fF][0-9a-fA-F]{2}|[^fF][fF][0-9a-fA-F]{2}|[0-9a-fA-F]{0,3}|:):.+';
            pattern '([^fF][0-9a-fA-F]{3}|[fF][^eE][0-9a-fA-F]{2}|[fF][eE][^8][0-9a-fA-F]|[fF][eE][8][^0]|[0-9a-fA-F]{0,3}|:):.+';
            pattern '([^0fF].*|0[^0fF].*|0{2}[^0fF].*|0{3}[^fF].*|0{0,2}[fF][^:].+|(0{0,3}[fF]:(0{0,4}:){0,6}|'
                  +  '0{0,3}[fF]:(0{0,4}:){0,6}([^0fF:].*|0[^0fF:].*|0{2}[^0fF:].*|0{3}[^fF:].*|0{0,2}[fF].+|0{1,4})))'
                  + '(%.+)?';
            pattern '([^0:].*|[0]{1,3}[^:0].*|(0{0,4}:){1,7}([^01:].*|0{1,3}[^01:].*|0{1,3}1[0-9a-fA-F]{0,2}:.*|'
                  + '1.+|:(0{0,3}[^01]|[^01].*|0[^01].+|00[^0].+|01.+|1.+)))'
                  + '(%.+)?';
        }
        description
            "An IPv6 address excluding all reserved address";
    }

    typedef interface-type {
      type string {
          pattern
              'ifp-([0-9])/([0-9])/([0-9]|[1-9][0-9])|memif-([0-9])/([0-9])/([0-9]|[1-9][0-9])|dpdk-([0-9])/([0-9])/([0-9]|[1-9][0-9])'
              + '|lo-([0-9])/([0-9])/([0-9]|[1-9][0-9])|hostif-([0-9])/([0-9])/([0-9]|[1-9][0-9])'
              + '|lag-([0-9]|[1-9][0-9])|all';
      }
      description
        "An Interface type";
    }

    typedef lag-interface-type {
      type string {
          pattern
              'lag-([0-9]|[1-9][0-9])';
      }
      description
        "Link-aggregation Interface type";
    }

    typedef lag-member-interface-type {
      type string {
          pattern
              'ifp-([0-9])/([0-9])/([0-9]|[1-9][0-9])|hostif-([0-9])/([0-9])/([0-9]|[1-9][0-9])|dpdk-([0-9])/([0-9])/([0-9]|[1-9][0-9])|memif-([0-9])/([0-9])/([0-9]|[1-9][0-9])';
      }
      description
        "Link-aggregation Member Interface type";
    }

    typedef logical-interface-type {
      type string {
          pattern
              'ifl-([0-9])/([0-9])/([0-9]|[1-9][0-9])/([0-9]|[1-9][0-9]|[1-9][0-9][0-9]|[1-3][0-9][0-9][0-9]|[4][0][0-9][0-6])'
	      + '|dpdk-([0-9])/([0-9])/([0-9]|[1-9][0-9])/([0-9]|[1-9][0-9]|[1-9][0-9][0-9]|[1-3][0-9][0-9][0-9]|[4][0][0-9][0-6])'
              + '|memif-([0-9])/([0-9])/([0-9]|[1-9][0-9])/([0-9]|[1-9][0-9]|[1-9][0-9][0-9]|[1-3][0-9][0-9][0-9]|[4][0][0-9][0-6])'
              + '|lo-([0-9])/([0-9])/([0-9]|[1-9][0-9])/([0-9]|[1-9][0-9]|[1-9][0-9][0-9]|[1-3][0-9][0-9][0-9]|[4][0][0-9][0-6])'
              + '|hostif-([0-9])/([0-9])/([0-9]|[1-9][0-9])/([0-9]|[1-9][0-9]|[1-9][0-9][0-9]|[1-3][0-9][0-9][0-9]|[4][0][0-9][0-6])'
              + '|lag-([0-9]|[1-9][0-9])/([0-9]|[1-9][0-9]|[1-9][0-9][0-9]|[1-3][0-9][0-9][0-9]|[4][0][0-9][0-6])';
      }
      description
        "Logical Interface type";
    }

    typedef string4096 {
        type string {
            length "1..4096";
        }
        description "String with max 4096 length";
    }

    typedef string2048 {
        type string {
            length "1..2048";
        }
        description "String with max 2048 length";
    }

    typedef string1024 {
        type string {
            length "1..1024";
        }
        description "String with max 1024 length";
    }

    typedef string512 {
        type string {
            length "1..512";
        }
        description "String with max 512 length";
    }

    typedef string128 {
        type string {
            length "1..128";
        }
        description "String with max 128 length";
    }

    typedef string64 {
        type string {
            length "1..64";
        }
        description "String with max 64 length";
    }

    typedef string48 {
        type string {
            length "1..48";
        }
        description "String with max 48 length";
    }

    typedef mpls-label {
        type uint32 {
            range "0 .. 1048575";
        }
        description "Mpls label value should be in the range 0 - 2^20-1";
    }

    typedef rtb-unicast-mac-type {
        type string {
            pattern "[0-9a:fA-F][02468aAcCeE](:[0-9a:fA-F]{2}){5}";
        }
        description
            "A unicast destination MAC address. The I/G address bit is
            used to identify the destination MAC address as an individual
            MAC address or a group MAC address. If the I/G address bit is
            0, it indicates that the MAC address field is an individual
            MAC address. If this bit is 1, the MAC address is a group MAC
            address that identifies one or more (or all) stations
            connected to the IEEE 802 network";
    }

    typedef vlan-encapsulation-type {
        type enumeration {
            enum 802.1q {
                value "0";
                description "802.1q encapsulation";
            }

            enum 802.1ad {
                value "1";
                description "802.1ad encapsulation";
            }
        }
        description "Vlan encapsulation";
    }

    typedef type-ipproto-acl {
        type enumeration {
            enum "HOPOPT" {
                value 0;
                description "HOPOPT";
            }
            enum "ICMP" {
                value 1;
                description "ICMP";
            }
            enum "IGMP" {
                value 2;
                description "IGMP";
            }
            enum "GGP" {
                value 3;
                description "GGP";
            }
            enum "IP_in_IP" {
                value 4;
                description "IP_in_IP";
            }
            enum "ST" {
                value 5;
                description "ST";
            }
            enum "TCP" {
                value 6;
                description "TCP";
            }
            enum "CBT" {
                value 7;
                description "CBT";
            }
            enum "EGP" {
                value 8;
                description "EGP";
            }
            enum "IGP" {
                value 9;
                description "IGP";
            }
            enum "BBN_RCC_MON" {
                value 10;
                description "BBN_RCC_MON";
            }
            enum "NVP_II" {
                value 11;
                description "NVP_II";
            }
            enum "PUP" {
                value 12;
                description "PUP";
            }
            enum "ARGUS" {
                value 13;
                description "ARGUS";
            }
            enum "EMCON" {
                value 14;
                description "EMCON";
            }
            enum "XNET"{
                value 15;
                description "XNET";
            }
            enum "CHAOS" {
                value 16;
                description "CHAOS";
            }
            enum "UDP" {
                value 17;
                description "UDP";
            }
            enum "MUX" {
                value 18;
                description "MUX";
            }
            enum "DCN_MEAS" {
                value 19;
                description "DCN_MEAS";
            }
            enum "HMP" {
                value 20;
                description "HMP";
            }
            enum "PRM" {
                value 21;
                description "PRM";
            }
            enum "XNS_IDP" {
                value 22;
                description "XNS_IDP";
            }
            enum "TRUNK_1" {
                value 23;
                description "TRUNK_1";
            }
            enum "TRUNK_2" {
                value 24;
                description "TRUNK_2";
            }
            enum "LEAF_1" {
                value 25;
                description "LEAF_1";
            }
            enum "LEAF_2" {
                value 26;
                description "LEAF_2";
            }
            enum "RDP" {
                value 27;
                description "RDP";
            }
            enum "IRTP" {
                value 28;
                description "IRTP";
            }
            enum "ISO_TP4" {
                value 29;
                description "ISO_TP4";
            }
            enum "NETBLT" {
                value 30;
                description "NETBLT";
            }
            enum "MFE_NSP" {
                value 31;
                description "MFE_NSP";
            }
            enum "MERIT_INP" {
                value 32;
                description "MERIT_INP";
            }
            enum "DCCP" {
                value 33;
                description "DCCP";
            }
            enum "3PC" {
                value 34;
                description "3PC";
            }
            enum "IDPR" {
                value 35;
                description "IDPR";
            }
            enum "XTP" {
                value 36;
                description "XTP";
            }
            enum "DDP" {
                value 37;
                description "DDP";
            }
            enum "IDPR_CMTP" {
                value 38;
                description "IDPR_CMTP";
            }
            enum "TP_PLUS_PLUS" {
                value 39;
                description "TP_PLUS_PLUS";
            }
            enum "IL" {
                value 40;
                description "IL";
            }
            enum "IPv6" {
                value 41;
                description "IPv6";
            }
            enum "SDRP" {
                value 42;
                description "SDRP";
            }
            enum "IPv6_Route" {
                value 43;
                description "IPv6_Route";
            }
            enum "IPv6_Frag" {
                value 44;
                description "IPv6_Frag";
            }
            enum "IDRP" {
                value 45;
                description "IDRP";
            }
            enum "RSVP" {
                value 46;
                description "RSVP";
            }
            enum "GREs" {
                value 47;
                description "GREs";
            }
            enum "DSR" {
                value 48;
                description "DSR";
            }
            enum "BNA" {
                value 49;
                description "BNA";
            }
            enum "ESP" {
                value 50;
                description "ESP";
            }
            enum "AH" {
                value 51;
                description "AH";
            }
            enum "I_NLSP" {
                value 52;
                description "I_NLSP";
            }
            enum "SWIPE" {
                value 53;
                description "SWIPE";
            }
            enum "NARP" {
                value 54;
                description "NARP";
            }
            enum "MOBILE IP" {
                value 55;
                description "MOBILE IP";
            }
            enum "TLSP" {
                value 56;
                description "TLSP";
            }
            enum "SKIP" {
                value 57;
                description "SKIP";
            }
            enum "IPv6_ICMP" {
                value 58;
                description "IPv6_ICMP";
            }
            enum "IPv6_NoNxt" {
                value 59;
                description "IPv6_NoNxt";
            }
            enum "IPv6_Opts" {
                value 60;
                description "IPv6_Opts";
            }
            enum "Any_host_internal_protocol" {
                value 61;
                description "Any host internal protocol";
            }
            enum "CFTP" {
                value 62;
                description "CFTP";
            }
            enum "Any_local_network" {
                value 63;
                description "Any local network";
            }
            enum "SAT_EXPAK" {
                value 64;
                description "SAT_EXPAK";
            }
            enum "KRYPTOLAN" {
                value 65;
                description "KRYPTOLAN";
            }
            enum "RVD" {
                value 66;
                description "RVD";
            }
            enum "IPPC" {
                value 67;
                description "IPPC";
            }
            enum "Any_distributed_file_system" {
                value 68;
                description "Any distributed file system";
            }
            enum "SAT_MON" {
                value 69;
                description "SAT_MON";
            }
            enum "VISA" {
                value 70;
                description "VISA";
            }
            enum "IPCU" {
                value 71;
                description "IPCU";
            }
            enum "CPNX" {
                value 72;
                description "CPNX";
            }
            enum "CPHB" {
                value 73;
                description "CPHB";
            }
            enum "WSN" {
                value 74;
                description "WSN";
            }
            enum "PVP" {
                value 75;
                description "PVP";
            }
            enum "BR_SAT_MON" {
                value 76;
                description "BR_SAT_MON";
            }
            enum "SUN_ND" {
                value 77;
                description "SUN_ND";
            }
            enum "WB_MON" {
                value 78;
                description "WB_MON";
            }
            enum "WB_EXPAK" {
                value 79;
                description "WB_EXPAK";
            }
            enum "ISO_IP" {
                value 80;
                description "ISO_IP";
            }
            enum "VMTP" {
                value 81;
                description "VMTP";
            }
            enum "SECURE_VMTP" {
                value 82;
                description "SECURE_VMTP";
            }
            enum "VINES" {
                value 83;
                description "VINES";
            }
            enum "TTP_IPTM" {
                value 84;
                description "TTP_IPTM";
            }
            enum "NSFNET_IGP" {
                value 85;
                description "NSFNET_IGP";
            }
            enum "DGP" {
                value 86;
                description "DGP";
            }
            enum "TCF" {
                value 87;
                description "TCF";
            }
            enum "EIGRP" {
                value 88;
                description "EIGRP";
            }
            enum "OSPF" {
                value 89;
                description "OSPF";
            }
            enum "Sprite_RPC" {
                value 90;
                description "Sprite_RPC";
            }
            enum "LARP" {
                value 91;
                description "LARP";
            }
            enum "MTP" {
                value 92;
                description "MTP";
            }
            enum "AX.25" {
                value 93;
                description "AX.25";
            }
            enum "OS" {
                value 94;
                description "OS";
            }
            enum "MICP" {
                value 95;
                description "MICP";
            }
            enum "SCC_SP" {
                value 96;
                description "SCC_SP";
            }
            enum "ETHERIP" {
                value 97;
                description "ETHERIP";
            }
            enum "ENCAP" {
                value 98;
                description "ENCAP";
            }
            enum "Any_private_encryption_scheme"{
                value 99;
                description "Any private encryption scheme";
            }
            enum "GMTP" {
                value 100;
                description "GMTP";
            }
            enum "IFMP" {
                value 101;
                description "IFMP";
            }
            enum "PNNI" {
                value 102;
                description "PNNI";
            }
            enum "PIM" {
                value 103;
                description "PIM";
            }
            enum "ARIS" {
                value 104;
                description "ARIS";
            }
            enum "SCPS" {
                value 105;
                description "SCPS";
            }
            enum "QNX" {
                value 106;
                description "QNX";
            }
            enum "A_N" {
                value 107;
                description "A_N";
            }
            enum "IPComp" {
                value 108;
                description "IPComp";
            }
            enum "SNP" {
                value 109;
                description "SNP";
            }
            enum "Compaq_Peer" {
                value 110;
                description "Compaq_Peer";
            }
            enum "IPX_in_IP" {
                value 111;
                description "IPX_in_IP";
            }
            enum "VRRP" {
                value 112;
                description "VRRP";
            }
            enum "PGM" {
                value 113;
                description "PGM";
            }
            enum "Any_0_hop_protocol"{
                value 114;
                description "Any 0_hop protocol";
            }
            enum "L2TP" {
                value 115;
                description "L2TP";
            }
            enum "DDX" {
                value 116;
                description "DDX";
            }
            enum "IATP" {
                value 117;
                description "IATP";
            }
            enum "STP" {
                value 118;
                description "STP";
            }
            enum "SRP" {
                value 119;
                description "SRP";
            }
            enum "UTI" {
                value 120;
                description "UTI";
            }
            enum "SMP" {
                value 121;
                description "SMP";
            }
            enum "SM" {
                value 122;
                description "SM";
            }
            enum "PTP" {
                value 123;
                description "PTP";
            }
            enum "IS_IS" {
                value 124;
                description "IS_IS";
            }
            enum "FIRE"{
                value 125;
                description "FIRE";
            }
            enum "CRTP" {
                value 126;
                description "CRTP";
            }
            enum "CRUDP" {
                value 127;
                description "CRUDP";
            }
            enum "SSCOPMCE" {
                value 128;
                description "SSCOPMCE";
            }
            enum "IPLT" {
                value 129;
                description "IPLT";
            }
            enum "SPS" {
                value 130;
                description "SPS";
            }
            enum "PIPE" {
                value 131;
                description "PIPE";
            }
            enum "SCTP" {
                value 132;
                description "SCTP";
            }
            enum "FC" {
                value 133;
                description "FC";
            }
            enum "RSVP_E2E_IGNORE" {
                value 134;
                description "RSVP_E2E_IGNORE";
            }
            enum "Mobility_Header"{
                value 135;
                description "Mobility Header";
            }
            enum "UDPLite" {
                value 136;
                description "UDPLite";
            }
            enum "MPLS_in_IP" {
                value 137;
                description "MPLS_in_IP";
            }
            enum "manet" {
                value 138;
                description "manet";
            }
            enum "HIP" {
                value 139;
                description "HIP";
            }
            enum "Shim6" {
                value 140;
                description "Shim6";
            }
            enum "WESP" {
                value 141;
                description "WESP";
            }
            enum "ROH" {
                value 142;
                description "ROH";
            }
        }
        description "ip protocol type";
    }

    typedef log-level {
        type enumeration {
            enum emergency {
                value "0";
                description "emergency";
            }
            enum alert {
                value "1";
                description "alert";
            }
            enum critical {
                value 2;
                description "critical";
            }
            enum error {
                value 3;
                description "error";
            }
            enum warning {
                value "4";
                description "warning";
            }
            enum notice {
                value "5";
                description "notice";
            }
            enum info {
                value "6";
                description "info";
            }
            enum debug {
                value "7";
                description "debug";
            }
            enum none {
                value "8";
                description "none";
            }

        }
        description "Log level";
    }
}
