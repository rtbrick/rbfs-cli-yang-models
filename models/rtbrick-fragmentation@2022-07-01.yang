submodule rtbrick-fragmentation {
    yang-version 1.1;

    belongs-to rtbrick-config {
        prefix config;
    }

    organization
      "Rtbrick";

    contact
      "Author : Sudhir C R (sudhir@rtbrick.com)";

    description
      "This module describes the YANG model for the fragmentation configuration.";

    revision 2022-07-01 {
        description
        "Configuration hierarchy for fragmentation";

        reference "None";
    }

    typedef fragmentation-afi {
        type enumeration {
            enum ipv4 {
                value "0";
                description "IPv4 address family";
            }
        }
        description "Fragmentation address family";
    }

    typedef state {
        type enumeration {
            enum disabled {
                value "0";
                description "Fragmentation disabled";
            }
            enum cpu {
                value "1";
                description "Software Fragmentation";
            }
        }
        description "Fragmentation state";
    }

    grouping fragmentation-top {
        description
            "Top-level fragmentation configuration";
        container fragmentation {
            description
                "Fragmentation configuration";
            container ipv4 {
                description
                    "Fragmentation configuration for IPv4 address family";
                reference
                '{
                    "table-getter": {
                        "library" : "libcmdfib.so",
                        "symbol"  : "fib_cmd_yang_get_fragmentation_cfg_tbl_templ",
                        "type"    : "fragmentation_cfg_table",
                        "default-attribute" : [ { "type" : "ipv4"} ]
                    }
                }';

                leaf state {
                    type state;
                    description
                        "Fragmentation state";
                    reference
                    '{
                        "attribute-getter" : {
                            "attribute" : "state"
                        }
                    }';
                }
            }
        }
    }
}
