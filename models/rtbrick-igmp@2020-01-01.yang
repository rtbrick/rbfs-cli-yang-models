submodule rtbrick-igmp {
    yang-version 1.1;

    belongs-to rtbrick-config {
        prefix config;
    }

    organization
        "Rtbrick";

    contact
        "Authors: Bhishma Acharya (bhishma@rtbrick.com)";

    description
        "This module contains the dummy YANG model for the IGMP protocol configuration";

    revision 2020-01-01 {
        description "First revision of dummy IGMP configuration";
        reference "None";
    }

    grouping igmp-multicast-options-top {
        description "This is dummy grouping for igmp-multicast-options. This is accessed in spine image";
    } //igmp-multicast-options-top


    grouping igmp-top {
        description "This grouping define dummy top-level IGMP model data. This is accessed in spine image";
    }//grouping igmp-top
}
