submodule rtbrick-mtu {
    yang-version 1.1;

    belongs-to rtbrick-config {
        prefix config;
    }

    import rtbrick-types {
        prefix "rtb-types";
    }

    organization "Rtbrick";

    contact
      "Authors: Ganesh Nagesh Naik (ganesh@rtbrick.com)";

    description
      "This module defines configuration and operational state data
      related to network MTU profile.";

    revision "2022-03-04" {
      description
        "First revision of MTU configuration";
      reference
        "None";
    }

    typedef type-mtu-type {
        type enumeration {
            enum "physical" {
                value 1;
                description "physical";
            }
            enum "pppoe" {
                value 2;
                description "pppoe";
            }
            enum "ipv4" {
                value 3;
                description "ipv4";
            }
            enum "ipv6" {
                value 4;
                description "ipv6";
            }
            enum "ip" {
                value 5;
                description "ip";
            }
        }
        description "mtu profile attachment type";
    }

    typedef type-mtu-action {
        type enumeration {
            enum "drop" {
                value 1;
                description "Action drop";
            }
            enum "redirect-to-cpu" {
                value 2;
                description "Action redirect-to-cpu";
            }
        }
        description "mtu profile action";
    }

    grouping mtu-profile-top {
        description
            "Top-level grouping for MTU profile configuration";
        list mtu-profile {
            key 'mtu-profile-name';
            description
                "Configure MTU profile";
            reference
                '{
                    "table-getter": {
                        "library" : "libcmdifmd.so",
                        "symbol"  : "ifm_yang_get_mtu_profile_tbl_templ",
                        "type"    : "mtu_profile_config_table"
                    }
                }';
            leaf mtu-profile-name {
                type rtb-types:string64;
                description
                    "Configure mtu profile name";
                reference
                '{
                    "attribute-getter" : {
                        "attribute" : "mtu_profile_name"
                    }
                }';
            }
            leaf size {
                type uint16 {
                     range "64 .. 9216";
                }
                mandatory true;
                description
                    "Configure mtu size";
                reference
                '{
                    "attribute-getter" : {
                        "attribute" : "mtu_size"
                    }
                }';
            }
            leaf type {
                type type-mtu-type;
                mandatory true;
                description
                    "Configure mtu type";
                reference
                '{
                    "attribute-getter" : {
                        "attribute" : "mtu_type"
                    }
                }';
            }
            leaf action {
                type type-mtu-action;
                mandatory true;
                description
                    "Configure mtu action";
                reference
                '{
                    "attribute-getter" : {
                        "attribute" : "mtu_action"
                    }
                }';
            }
        }
    }

} //module rtbrick-mtu
