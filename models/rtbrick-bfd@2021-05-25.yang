submodule rtbrick-bfd {
   yang-version 1.1;
 
   belongs-to rtbrick-config {
       prefix config;
   }

   import rtbrick-types {
       prefix "rtb-types";
   }

   organization
       "Rtbrick";
 
   contact
       "Authors: Bhishma Acharya (bhishma@rtbrick.com)";
 
   description
       "This module contains the YANG model for the BFD protocol configuration
       +-> global
       | +-> protocol
       |   +-> bfd
       |     +-> profile
       |       +-> minimum-interval
       |       +-> minimum-tx-interval
       |       +-> minimum-rx-interval
       |       +-> detect-multiplier
       +-> instance
         +-> interface
           +-> profile";
 
   revision 2021-05-25 {
       description "First revision of BFD configuration";
       reference "None";
   }
 
   grouping bfd-config-attributes {
       description "Grouping of BFD configurable attributes";
 
       leaf minimum-interval {
           type uint16 {
               range "100 .. 1000";
           }
           description " Minimum transmit and receive interval in milliseconds. Default: 200ms";
           reference
               '{
                   "attribute-getter" : {
                       "attribute" : "minimum_interval"
                   }
               }';
       } // minimum-interval
 
       leaf minimum-tx-interval {
           type uint16 {
               range "100 .. 1000";
           }
           description " Minimum transmit interval in milliseconds. Default: 200ms";
           reference
               '{
                   "attribute-getter" : {
                       "attribute" : "minimum_tx_interval"
                   }
               }';
       } // minimum-tx-interval
 
       leaf minimum-rx-interval {
           type uint16 {
               range "100 .. 1000";
           }
           description " Minimum receive interval in milliseconds. Default: 200ms";
           reference
               '{
                   "attribute-getter" : {
                       "attribute" : "minimum_rx_interval"
                   }
               }';
       } // minimum-tx-interval
 
       leaf multiplier {
           type uint16 {
               range "1 .. 255";
           }
           description " Detection time multiplier. Default: 3";
           reference
               '{
                   "attribute-getter" : {
                       "attribute" : "detect_multiplier"
                   }
               }';
       } //detect-multiplier
   }//grouping bfd-config-attributes

   grouping bfd-global-top {
       description "This grouping to define top-level BFD configuration model";
       container bfd {
           description "Protocol BFD global-profile configuration";

           list profile {
               key "profile";
               description "BFD profile name";
               reference
                   '{
                       "table-getter": {
                           "library": "libbfd-cmd.so",
                           "symbol": "bfd_config_yang_profile_table_templ",
                           "type" :  "bfd_profile_config_table"
                       }
                   }';
               leaf profile {
                   type string {
                       pattern
                           '[a-zA-Z_][a-zA-Z0-9_]{0,64}';
                       length "1..64";
                   }

                   description "BFD profile name";
                   reference
                       '{
                           "attribute-getter" : {
                               "attribute" : "profile"
                           }
                       }';
               }//leaf profile
               uses bfd-config-attributes;
           }//list profile
       }//container bfd
   }//grouping bfd-global-top
 
   grouping bfd-top {
       description "This grouping to define top-level BFD configuration model";
       container bfd {
           description "Protocol BFD configuration";
           list interface {
               key "interface-name";
               description "BFD interface configuration";
               reference
                   '{
                       "table-getter": {
                           "library": "libbfd-cmd.so",
                           "symbol": "bfd_config_yang_interface_table_templ",
                           "type" :  "bfd_interface_config_table",
                           "inherit-attribute":["instance_name"]
                       }
                   }';
               leaf interface-name {
                   type rtb-types:logical-interface-type;
                   description "Reference to an entry in the global interface list";
                   reference
                       '{
                           "attribute-getter" : {
                               "attribute" : "interface_name",
                               "expansion-getter" : {
                                   "package":"bfd",
                                   "method" : "bfd_logical_interface_name_expander"
                               }
                           }
                       }';
               }//leaf interface-name
              leaf profile {
                   type string {
                       pattern
                           '[a-zA-Z_][a-zA-Z0-9_]{0,64}';
                       length "1..64";
                   }
                   description "BFD profile name";
                   reference
                       '{
                           "attribute-getter" : {
                               "attribute" : "profile",
                               "expansion-getter" : {
                                   "package":"bfd",
                                   "method" : "bfd_profile_name_expander"
                               }
                           }
                       }';
               }//leaf profile
           }//list interface
       }//container bfd
   }//grouping bfd-top
}
