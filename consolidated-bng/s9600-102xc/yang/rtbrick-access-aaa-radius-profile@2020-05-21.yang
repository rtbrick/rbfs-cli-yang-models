submodule rtbrick-access-aaa-radius-profile {

    yang-version 1.1;                                                                

    belongs-to rtbrick-config {
        prefix config;
    }

    import ietf-inet-types {
        prefix "inet";
        reference "RFC 6991";
    }
    import rtbrick-types {
        prefix "rtb-types";
    }

    organization
      "RtBrick";
    contact
      "Authors: Vyshakh Krishnan (vyshakh@rtbrick.com)";
    description
      "This sub-module contains yang structure for
       access AAA RADIUS profile.";
    revision 2020-05-21 {
        description "First revision";
        reference "None";
    }

    typedef nas-port-format {
        type enumeration {
            enum DEFAULT {
                value "0";
                description "Default port format";
            }
            enum SLOTS {
                value "1";
                description "Slot format";
            }
        }
        description "NAS-Port format";
    }

    typedef nas-port-type {
        type enumeration {
            enum Virtual {
                value "0";
                description "Virtual";
            }
            enum SDSL {
                value "1";
                description "SDSL";
            }
            enum ADSL-CAP {
                value "2";
                description "SDSL";
            }
            enum ADSL-DMT {
                value "3";
                description "SDSL";
            }
            enum Ethernet {
                value "4";
                description "Ethernet";
            }
            enum xDSL {
                value "5";
                description "xDSL";
            }
            enum Cable {
                value "6";
                description "Cable";
            }
            enum PPPoA {
                value "7";
                description "PPPoA";
            }
            enum PPPoEoA {
                value "8";
                description "PPPoEoA";
            }
            enum PPPoEoE {
                value "9";
                description "PPPoEoE";
            }
            enum PPPoEoVLAN {
                value "10";
                description "PPPoEoVLAN";
            }
            enum PPPoEoQinQ {
                value "11";
                description "PPPoEoQinQ";
            }
            enum xPON {
                value "12";
                description "xPON";
            }
        }
        description "NAS-Port type";
    }

    typedef algorithm-type {
        type enumeration {
            enum DIRECT {
                value "0";
                description "Direct algorithm";
            }
            enum ROUND-ROBIN {
                value "1";
                description "Round Robin algorithm";
            }
        }
        description "Algorithm type";
    }

    grouping access-aaa-radius-profile {
        description "Global access RADIUS profile configuration";

        list radius-profile {
            key "profile-name";
            description "Global AAA RADIUS profile configuration";
            reference
            '{
                "table-getter": {
                    "table-name" : "global.access.aaa.radius.config",
                    "type"    : "aaa_radius_profile_config_table"
                }
            }';
            leaf profile-name {
                type string {
                    length "1..64";
                }
                description "Name of the RADIUS profile";
                reference
                '{
                    "attribute-getter" : {
                        "attribute" : "aaa_radius_profile_name"
                    }
                }';
            }
            leaf nas-identifier {
                type string {
                    length "1..64";
                }
                description "NAS identifier";
                reference
                '{
                    "attribute-getter" : {
                       "attribute" : "nas_identifier"
                    }
                }';
            }
            leaf nas-ip-address {
                type inet:ipv4-address;
                description "NAS IP address (IPv4 Address)";
                reference
                '{
                    "attribute-getter" : {
                        "attribute" : "nas_ip_address"
                    }
                }';
            }
            leaf nas-port-format {
                type nas-port-format;
                description "NAS-Port format";
                reference
                '{
                    "attribute-getter" : {
                        "attribute" : "nas_port_format"
                    }
                }';
            }
            leaf nas-port-type {
                type nas-port-type;
                description "NAS-Port type";
                reference
                '{
                    "attribute-getter" : {
                        "attribute" : "nas_port_type"
                    }
                }';
            }
            container authentication {
                description "RADIUS authentication options";
                reference
                '{
                    "table-getter": {
                        "table-name" : "global.access.aaa.radius.config",
                        "type"    : "aaa_radius_profile_config_table",
                        "inherit-attribute": ["aaa_radius_profile_name"]
                    }
                }';
                leaf-list radius-server-profile-name {
                    type string {
                        length "1..64";
                    }
                    description "RADIUS server profile name";
                    reference
                    '{
                        "attribute-getter" : {
                            "attribute" : "authentication_server_list"
                        }
                    }';
                }
                leaf algorithm-type {
                    type algorithm-type;
                    description "Authentication redundancy algorithm";
                    reference
                    '{
                        "attribute-getter" : {
                            "attribute" : "authentication_algorithm"
                        }
                    }';
                }
            }
            container accounting {
                description "RADIUS accounting options";
                reference
                '{
                    "table-getter": {
                        "table-name" : "global.access.aaa.radius.config",
                        "type"    : "aaa_radius_profile_config_table",
                        "inherit-attribute": ["aaa_radius_profile_name"]
                    }
                }';
                leaf-list radius-server-profile-name {
                    type string {
                        length "1..64";
                    }
                    description "RADIUS server profile name";
                    reference
                    '{
                        "attribute-getter" : {
                            "attribute" : "accounting_server_list"
                        }
                    }';
                }
                leaf algorithm-type {
                    type algorithm-type;
                    description "Accounting redundancy algorithm";
                    reference
                    '{
                        "attribute-getter" : {
                            "attribute" : "accounting_algorithm"
                        }
                    }';
                }
                leaf stop-on-reject {
                    type rtb-types:boolean-type;
                    description "Send accounting-stop on authentication reject";
                    reference
                    '{
                        "attribute-getter" : {
                            "attribute" : "accounting_stop_on_reject"
                        }
                    }';
                }
                leaf stop-on-failure {
                    type rtb-types:boolean-type;
                    description "Send accounting-stop on failure";
                    reference
                    '{
                        "attribute-getter" : {
                            "attribute" : "accounting_stop_on_failure"
                        }
                    }';
                }
                leaf accounting-on-off {
                    type rtb-types:boolean-type;
                    description "Enable accounting on/off";
                    reference
                    '{
                        "attribute-getter" : {
                            "attribute" : "accounting_on_off"
                        }
                    }';
                }
                leaf accounting-on-wait {
                    type rtb-types:boolean-type;
                    description "Wait for accounting-on response before sending authentication requests";
                    reference
                    '{
                        "attribute-getter" : {
                            "attribute" : "accounting_on_wait"
                        }
                    }';
                }
                leaf accounting-backup {
                    type rtb-types:boolean-type;
                    description "Enable backup accounting";
                    reference
                    '{
                        "attribute-getter" : {
                            "attribute" : "accounting_backup"
                        }
                    }';
                }
                leaf accounting-backup-max {
                    type uint32;
                    description "Max backup accounting hold time in seconds <1-4294967295>";
                    reference
                    '{
                        "attribute-getter" : {
                            "attribute" : "accounting_backup_max"
                        }
                    }';
                }
            }
        }
    }
}
