submodule rtbrick-access-dhcp-server {

    yang-version 1.1;

    belongs-to rtbrick-config {
        prefix config;
    }

    import ietf-inet-types {
        prefix "inet";
        reference "RFC 6991";
    }

    organization
      "RtBrick";
    contact
      "Authors: Vyshakh Krishnan (vyshakh@rtbrick.com)";
    description
      "This sub-module contains yang structure for
       DHCP server configurations.";
    revision 2021-04-12 {
        description "First revision";
        reference "None";
    }

    grouping access-dhcp-server {
        description "Global access DHCP server configuration";
        
        list dhcp-server {
            key "server-name";
            description "Global DHCP server configuration";
            reference
            '{
                "table-getter": {
                    "table-name" : "global.access.dhcp.server.config",
                    "type"    : "dhcp_server_config_table"
                }
            }';                                                      
            leaf server-name {
                type string {
                    length "1 .. 64";
                }
                description "Name of the DHCP server";
                reference
                '{
                    "attribute-getter" : {
                        "attribute" : "dhcp_server_name"
                    }
                }';
            }
            leaf address {
                type inet:ipv4-address;
                description "DHCP server address";
                reference
                '{
                    "attribute-getter" : {
                        "attribute" : "dhcp_server_ipv4_address"
                    }
                }';
            } 
            leaf source-address {
                type inet:ipv4-address;
                description "Source address used for DHCP packets";
                reference
                '{
                    "attribute-getter" : {
                        "attribute" : "local_source_ipv4_address"
                    }
                }';
            }
            leaf routing-instance {
                type string {
                    length "1 .. 64";
                }
                description "Instance name from which DHCP server is reachable";
                reference
                '{
                    "attribute-getter" : {
                        "attribute" : "instance",
                        "expansion-getter" : {
                            "package":"subsMgmt",
                            "method" :"access_instance_name_expander"
                        }
                    }
                }';
            }
        }   
    }
}
