submodule rtbrick-ldp {
    yang-version 1.1;
    belongs-to rtbrick-config {
        prefix config;
    }

    import ietf-inet-types {
        prefix "inet";
    }
    import rtbrick-types {
        prefix "rtb-types";
    }
    import rtbrick-ldp-types {
        prefix "rtb-ldp-types";
    }

    organization "RtBrick";

    contact
      "Authors: Akshath TR (akshath@rtbrick.com)";

    description
        "This module describes a YANG model for LDP configuration.

    This model supports the following LDP configuration level
    hierarchy:

      LDP
        |
        +-> [ Global LDP configuration ]
          +-> Interface
          +-> Peer
            +-> Redistribute";

    revision "2022-08-09" {
      description
        "First revision of LDP configuration";
      reference
        "None";

    }

    grouping ldp-loop-detection {
        container loop-detection {
        description
            "LDP loop detection configurations";
            reference
            '{
                "table-getter": {
                    "table-name": "global.ldp.instance.config",
                    "type" :   "ldp_instance_config_table",
                    "inherit-attribute":["instance_name"]
                }
            }';
            leaf status {
                type rtb-types:enable-disable-type;
                description "Loop detection status";
                reference
                '{
                    "attribute-getter" : {
                        "attribute" : "loop_detection_status"
                    }
                }';
            }
            leaf hop-count {
                type uint8;
                description "Hop count, <1-255>, default 32";
                reference
                '{
                    "attribute-getter" : {
                        "attribute" : "loop_detection_hop_count"
                    }
                }';
            }
            leaf vector-length {
                type uint8;
                description "Max vector length limit, <1-255>, default 32";
                reference
                '{
                    "attribute-getter" : {
                        "attribute" : "loop_detection_vector_length"
                    }
                }';
            }
        } 
    }

    grouping ldp-policy {
        description "Policy map name";
        leaf-list policy {
            max-elements 10;
            ordered-by user;
            type string {
                length "1..64";
            }
            description "Policy map name";
            reference
            '{
                "attribute-getter" : {
                    "attribute" : "policy_name",
                    "expansion-getter" : {
                        "package":"ldp",
                        "method" : "ldp_policy_name_expander"
                     }
                }
            }';
        }
    }

    grouping ldp-address_family {
        list address-family {
            key "afi";
            description "LDP address family";
            reference
            '{
                "table-getter": {
                    "library": "libldpyang.so",
                    "symbol" : "ldp_yang_config_afi_tbl_templ",
                    "type"   : "ldp.afi.config",
                    "inherit-attribute":["instance_name"]
                }
            }';
            leaf afi {
                type rtb-ldp-types:afi;
                description "Afi type";
                reference
                '{
                    "attribute-getter": {
                        "attribute": "afi"
                    }
                }';
            }
            leaf status {
                type rtb-types:enable-disable-type;
                description "Afi status";
                reference
                '{
                    "attribute-getter": {
                        "attribute": "status"
                    }
                }';
            }
            uses ldp-redistribution;
        }
    }

    grouping ldp-redistribution {
        description
            "This grouping defines LDP redistribution releated configurations";
        list redistribute {
            key "source";
            description "Redistribution configuration";
            reference
            '{
                "table-getter": {
                    "library": "libldpyang.so",
                    "symbol" : "ldp_yang_config_redist_tbl_templ",
                    "type"   : "ldp.protocolinfra.redistribution_table",
                    "inherit-attribute":["instance_name","afi"]
                }
            }';
            leaf source {
                type rtb-ldp-types:rib-source;
                description "Source protocol";
                reference
                '{
                    "attribute-getter" : {
                        "attribute" : "source"
                    }
                }';
            }
            uses ldp-policy;
        }
    }

    grouping ldp-interface {
        description
            "This grouping defines LDP interface related configuration";
        list interface {
            key "name";
            description "LDP interface configuration";
            reference
            '{
                "table-getter": {
                    "library": "libldpyang.so",
                    "symbol":  "ldp_yang_config_interface_tbl_templ",
                    "type" :   "ldp_interface_config_table"
                }
            }';
            leaf name {
                type string {
                    length "1..64";
                }
                description "Logical interface name";
                reference
                '{
                    "attribute-getter" : {
                        "attribute" : "ifname",
                        "expansion-getter" : {
                            "package":"ldp",
                            "method" : "ldp_ifname_expander"
                        }
                    }
                }';
            }
        }
    }

    grouping ldp-hello {
        container hello {
            description "LDP hello configurations";
            reference
            '{
                "table-getter": {
                    "table-name": "global.ldp.instance.config",
                    "type" :   "ldp_instance_config_table",
                    "inherit-attribute":["instance_name"]
                }
            }';
            leaf interval {
                type uint16;
                description "Hello messages interval, <0-65535>";
                reference
                '{
                    "attribute-getter" : {
                        "attribute" : "discovery_hello_interval"
                    }
                }';
            }
            leaf hold-time {
                type uint16;
                description "Hold interval before declaring a neighbor to be down, <0-65535>";
                reference
                '{
                    "attribute-getter" : {
                        "attribute" : "discovery_hold_interval"
                    }
                }';
            }
        }
    }

    grouping ldp-targeted-hello-timer {
        container targeted-hello {
            description "LDP targeted neighbor configurations";
            reference
            '{
                "table-getter": {
                    "table-name": "global.ldp.instance.config",
                    "type" :   "ldp_instance_config_table",
                    "inherit-attribute":["instance_name"]
                }
            }';
            leaf interval {
                type uint16;
                description "Targeted hello messages interval, <0-65535>, default 15s";
                reference
                '{
                    "attribute-getter" : {
                        "attribute" : "targeted_hello_interval"
                    }
                }';
            }
            leaf hold-time {
                type uint16;
                description "Targeted hold time, <0-65535>, default 45s";
                reference
                '{
                    "attribute-getter" : {
                        "attribute" : "targeted_hold_interval"
                    }
                }';
            }
        }
    }

    grouping ldp-targeted-neighbor {
        container targeted-neighbor {
            description "LDP targeted neighbor configuration";
            list ipv4 {
                key "neighbor-address source-address";
                description "IPv4 targeted neighbor";
                reference
                '{
                    "table-getter": {
                        "library": "libldpyang.so",
                        "symbol":  "ldp_yang_config_nbr_tbl_templ",
                        "type" :   "ldp_nbr_config_table"
                    }
                }';
                leaf neighbor-address {
                    type inet:ipv4-address-no-zone;
                    description "Targeted neighbor address";
                    reference
                    '{
                        "attribute-getter" : {
                            "attribute" : "nbr_address"
                        }
                    }';
                }
                leaf source-address{
                    type inet:ipv4-address-no-zone;
                    description "Source address for targeted TCP session";
                    reference
                    '{
                        "attribute-getter" : {
                            "attribute" : "src_address"
                        }
                    }';
                }
                leaf connection-preference {
                    type rtb-ldp-types:afi;
                    description "Transport connection preference";
                    reference
                    '{
                        "attribute-getter" : {
                            "attribute" : "transport_preference"
                        }
                    }';
                }
                leaf neighbor-type {
                    type rtb-ldp-types:nbr-type;
                    description "Neighbor type, sender or receiver";
                    reference
                    '{
                        "attribute-getter" : {
                            "attribute" : "nbr_type"
                        }
                    }';
                }
                leaf interval {
                    type uint16;
                    description "Targeted hello messages interval, <0-65535>, default 15s";
                    reference
                    '{
                        "attribute-getter" : {
                            "attribute" : "hello_interval"
                        }
                    }';
                }
                leaf hold-time {
                    type uint16;
                    description "Targeted hold time, <0-65535>, default 45s";
                    reference
                    '{
                        "attribute-getter" : {
                            "attribute" : "hold_interval"
                        }
                    }';
                }
            }
            list ipv6 {
                key "neighbor-address source-address";
                description "IPv6 targeted neighbor";
                reference
                '{
                    "table-getter": {
                        "library": "libldpyang.so",
                        "symbol":  "ldp_yang_config_nbr_tbl_templ",
                        "type" :   "ldp_nbr_config_table"
                    }
                }';
                leaf neighbor-address {
                    type inet:ipv6-address-no-zone;
                    description "Targeted neighbor address";
                    reference
                    '{
                        "attribute-getter" : {
                            "attribute" : "nbr_v6_address"
                        }
                    }';
                }
                leaf source-address {
                    type inet:ipv6-address-no-zone;
                    description "Source address for targeted TCP session";
                    reference
                    '{
                        "attribute-getter" : {
                            "attribute" : "src_v6_address"
                        }
                    }';
                }
                leaf connection-preference {
                    type rtb-ldp-types:afi;
                    description "Transport connection preference";
                    reference
                    '{
                        "attribute-getter" : {
                            "attribute" : "transport_preference"
                        }
                    }';
                }
                leaf neighbor-type {
                    type rtb-ldp-types:nbr-type;
                    description "Neighbor type, sender or receiver";
                    reference
                    '{
                        "attribute-getter" : {
                            "attribute" : "nbr_type"
                        }
                    }';
                }
                leaf interval {
                    type uint16;
                    description "Targeted hello messages interval, <0-65535>, default 15s";
                    reference
                    '{
                        "attribute-getter" : {
                            "attribute" : "hello_interval"
                        }
                    }';
                }
                leaf hold-time {
                    type uint16;
                    description "Targeted hold time, <0-65535>, default 45s";
                    reference
                    '{
                        "attribute-getter" : {
                            "attribute" : "hold_interval"
                        }
                    }';
                }
            }
        }
    }

    grouping ldp-session {
        container session {
            description "LDP session configurations";
            reference
            '{
                "table-getter": {
                    "table-name": "global.ldp.instance.config",
                    "type" :   "ldp_instance_config_table",
                    "inherit-attribute":["instance_name"]
                }
            }';
            leaf keepalive-interval {
                type uint16 {
                    range "1..65535";
                }
                description "Keepalive messages transmission interval, <1-65535>";
                reference
                '{
                    "attribute-getter" : {
                        "attribute" : "session_keepalive_interval"
                    }
                }';
            }
            leaf keepalive-timeout {
                type uint16 {
                    range "1..65535";
                }
                description "Hold interval before declaring a session to be down, <1-65535>";
                reference
                '{
                    "attribute-getter" : {
                        "attribute" : "session_hold_interval"
                    }
                }';
            }
        }
    }

    grouping ldp-timer {
        container timer {
            description "LDP timers configurations";
            reference
            '{
                "table-getter": {
                    "table-name": "global.ldp.instance.config",
                    "type" :   "ldp_instance_config_table",
                    "inherit-attribute":["instance_name"]
                }
            }';
            uses ldp-hello;
            uses ldp-targeted-hello-timer;
            uses ldp-session;
        }
    }

    grouping igp-synchronization {
        container igp-synchronization {
            description "LDP IGP synchronization configuration";
            reference
            '{
                "table-getter": {
                    "table-name": "global.ldp.instance.config",
                    "type" :   "ldp_instance_config_table",
                    "inherit-attribute":["instance_name"]
                }
            }';
            leaf hold-timer {
                type uint16;
                description "Hold interval before declaring a session to be synchronized, <0-60s>";
                reference
                '{
                    "attribute-getter" : {
                        "attribute" : "igp_sync_hold_time"
                    }
                }';
            }
        }
    }

    grouping source-address {
        container source-address {
            description "LDP source address for TCP session";
            reference
            '{
                "table-getter": {
                    "table-name": "global.ldp.instance.config",
                    "type" :   "ldp_instance_config_table",
                    "inherit-attribute":["instance_name"]
                }
            }';
            leaf ipv4 {
                type inet:ipv4-address-no-zone;
                description "Source address for TCP session";
                reference
                '{
                    "attribute-getter" : {
                        "attribute" : "transport_address"
                    }
                }';
            }
            leaf ipv6 {
                type inet:ipv6-address-no-zone;
                description "Source address for TCP session";
                reference
                '{
                    "attribute-getter" : {
                        "attribute" : "transport_v6_address"
                    }
                }';
            }
        }
    }

    grouping ldp-peer {
        description
            "This grouping defines LDP peer related configuration";
        container peer {
            description "LDP peer related configuration";
            list ipv4 {
                key "address";
                description "ipv4 address";
                reference
                '{
                    "table-getter": {
                        "library": "libldpyang.so",
                        "symbol":  "ldp_yang_config_peer_tbl_templ",
                        "type" :   "ldp_peer_config_table",
                        "inherit-attribute":["instance_name"]
                    }
                }';
                leaf address {
                    type inet:ipv4-address-no-zone;
                    description "LDP peer address";
                    reference
                    '{
                        "attribute-getter": {
                            "attribute": "peer_ipv4_transport_address"
                        }
                    }';
                }
                leaf authentication-id {
                    type string {
                        length "1..64";
                    }
                    description "Authentication Tuple Identifier";
                    reference
                    '{
                        "attribute-getter" : {
                            "attribute" : "auth_id"
                        }
                    }';
                }
                leaf export-policy {
                    type string {
                        length "1..64";
                    }
                    description "Import policy identifier";
                    reference
                    '{
                        "attribute-getter": {
                            "attribute" : "export_policy"
                        }
                    }';
                }
                leaf import-policy {
                    type string {
                        length "1..64";
                    }
                    description "Import policy identifier";
                    reference
                    '{
                        "attribute-getter": {
                            "attribute" : "import_policy"
                        }
                    }';
                }
            }
            list ipv6 {
                key "address";
                description "ipv6 address";
                reference
                '{
                    "table-getter": {
                        "library": "libldpyang.so",
                        "symbol":  "ldp_yang_config_peer_tbl_templ",
                        "type" :   "ldp_peer_config_table",
                        "inherit-attribute":["instance_name"]
                    }
                }';
                leaf address {
                    type inet:ipv6-address-no-zone;
                    description "LDP peer address";
                    reference
                    '{
                        "attribute-getter": {
                            "attribute": "peer_ipv6_transport_address"
                        }
                    }';
                }
                leaf authentication-id {
                    type string {
                        length "1..64";
                    }
                    description "Authentication Tuple Identifier";
                    reference
                    '{
                        "attribute-getter" : {
                            "attribute" : "auth_id"
                        }
                    }';
                }
                leaf export-policy {
                    type string {
                        length "1..64";
                    }
                    description "Import policy identifier";
                    reference
                    '{
                        "attribute-getter": {
                            "attribute" : "export_policy"
                        }
                    }';
                }
                leaf import-policy {
                    type string {
                        length "1..64";
                    }
                    description "Import policy identifier";
                    reference
                    '{
                        "attribute-getter": {
                            "attribute" : "import_policy"
                        }
                    }';
                }
            }
        }
    }

    grouping ldp-top {
        description
            "This grouping defines top-level LDP model data";
        container ldp {
            description "LDP related commands";
            reference
            '{
                "table-getter": {
                    "table-name": "global.ldp.instance.config",
                    "type" :   "ldp_instance_config_table",
                    "inherit-attribute":["instance_name"]
                }
            }';
            leaf router-id {
                type inet:ipv4-address-no-zone;
                description "LDP identifier(format: A.B.C.D)";
                reference
                '{
                    "attribute-getter" : {
                        "attribute" : "local_lsr_id"
                    }
                }';
            }
            leaf connection-preference {
                type rtb-ldp-types:afi;
                description "LDP transport connection preference";
                reference
                '{
                    "attribute-getter" : {
                        "attribute" : "transport_preference"
                    }
                }';
            }
            leaf dual-stack-interop {
                type rtb-types:enable-disable-type;
                description "To interop dual stack TLV with non RFC compliant vendors";
                reference
                '{
                    "attribute-getter" : {
                        "attribute" : "dual_stack_interop"
                    }
                }';
            }
            uses ldp-timer;
            uses ldp-loop-detection;
            //uses ldp-targeted-neighbor;
            uses ldp-interface;
            uses igp-synchronization;
            uses source-address;
            uses ldp-address_family;
            uses ldp-peer;
        }
    }
}
