submodule rtbrick-mirroring {
    yang-version 1.1;

    belongs-to rtbrick-config {
        prefix config;
    }

    import rtbrick-types {
        prefix "rtb-types";
    }

    organization
      "Rtbrick";

    contact
      "Author : Ganesh Nagesh Naik (ganesh@rtbrick.com)";

    description
      "This is the mirroring related configuration yang file";

    revision 2020-07-26 {
        description
        "Configuration hierarchy for mirroring";

        reference "None";
    }

    typedef type-direction-mirror {
        type enumeration {
            enum "ingress" {
                value 1;
                description "ingress direction";
            }
            enum "egress" {
                value 2;
                description "egress direction";
            }
        }
        description "direction data type";
    }

    typedef mirror-dest-interface-type {
      type string {
          length "1..64";
          pattern
              'ifp-([0-9])/([0-9])/([0-9]|[1-9][0-9]|[1-9][0-9][0-9])|cpu-(0/0/200)';
      }
      description
        "An mirror destination interface type, type supported ifp and specific cpu with name cpu-0/0/200";
    }

    typedef mirror-source-interface-type {
      type string {
          length "1..64";
          pattern
              'ifp-([0-9])/([0-9])/([0-9]|[1-9][0-9]|[1-9][0-9][0-9])'
              + '|ifp-([0-9])/([0-9])/([0-9]|[1-9][0-9]|[1-9][0-9][0-9])#([0-3])'
              + '|recycle-([0-9])/([0-9])/([0-9]|[1-9][0-9]|[1-9][0-9][0-9])';

      }
      description
        "An mirror destination interface type, type supported are ifp and recycle ";
    }

    typedef mirror-logical-interface-type {
      type string {
          length "1..64";
          pattern
              'ifl-([0-9])/([0-9])/([0-9]|[1-9][0-9])/([0-9]|[1-9][0-9]|[1-9][0-9][0-9]|[1-3][0-9][0-9][0-9]|[4][0][0-9][0-6])'
              + '|recycle-([0-9])/([0-9])/([0-9]|[1-9][0-9][0-9])/([0-9]|[1-9][0-9]|[1-9][0-9][0-9]|[1-3][0-9][0-9][0-9]|[4][0][0-9][0-6])';
      }
      description
        "Mirror Logical Interface type, type supported are ifp and recycle";
    }

    grouping source-group {
        description
            "Configure mirroring source.";
        container source {
            description
                "Configure source.";
            reference
            '{
                "table-getter": {
                    "table-name" : "global.mirror.config",
                    "type"    :  "global_mirror_config_table",
                    "inherit-attribute":[ "mirror_name" ]
                }
            }';
            leaf direction {
                type type-direction-mirror;
                description
                    "Configure traffic direction ingress/egress.";
                reference
                '{
                    "attribute-getter" : {
                        "attribute" : "mirror_stage"
                    }
                }';
            }
            leaf acl {
                type rtb-types:boolean-true;
                description
                    "Configure source as acl.";
                reference
                '{
                    "attribute-getter" : {
                        "attribute" : "mirror_acl"
                    }
                }';
            }
            leaf interface {
                must 'not (../logical-interface)' {
                    error-message "Mirror config failed as both source IFP and source IFL is not allowed";
                }
                type mirror-source-interface-type;
                description
                    "Configure source physical interface.";
                reference
                '{
                    "attribute-getter" : {
                        "attribute" : "mirror_source_ifp_name",
                        "expansion-getter" : {
                            "package":"ifm",
                            "method" :"ifm_mirror_source_ifp_name_expander"
                        }
                    }
                }';
            }
            leaf logical-interface {
                must 'not (../interface)' {
                    error-message "Mirror config failed as both source IFP and source IFL is not allowed";
                }
                type mirror-logical-interface-type;
                description
                    "Configure source logical interface name.";
                reference
                '{
                    "attribute-getter" : {
                        "attribute" : "mirror_source_ifl_name",
                        "expansion-getter" : {
                            "package":"ifm",
                            "method" :"ifm_mirror_source_ifl_name_expander"
                        }
                    }
                }';
            }
        }// container source
    }// grouping source-group

    grouping destination-group {
        description
            "Grouping for destination.";
        container destination {
            description
            "Container for destination parameters.";
            reference
            '{
                "table-getter": {
                    "table-name" : "global.mirror.config",
                    "type"    :  "global_mirror_config_table",
                    "inherit-attribute":[ "mirror_name" ]
                }
            }';
            leaf interface {
                type mirror-dest-interface-type;
                description
                    "Configure destination interface name.";
                reference
                '{
                    "attribute-getter" : {
                        "attribute" : "mirror_dest_ifp_name",
                        "expansion-getter" : {
                            "package":"ifm",
                            "method" :"ifm_mirror_destination_ifp_name_expander"
                        }
                    }
                }';
            }
        }// container destination
    }// grouping mirroring-type

    grouping mirroring-top {
        description
        "Top-level grouping containing a list of mirroring profile.";
        list mirror {
            key 'name';
            description
                "Configuration parameters relating to a top-level mirror profile";
            reference
            '{
                "table-getter": {
                    "table-name" : "global.mirror.config",
                    "type"    : "global_mirror_config_table"
                }
            }';
            leaf name {
                type string {
                    length "1..64";
                }
                description
                    "Configure mirror profile name.";
                reference
                '{
                    "attribute-getter" : {
                        "attribute" : "mirror_name"
                    }
                }';
            }

            uses destination-group;
            uses source-group;
        } // list mirror
    } // grouping mirroring-top
}
