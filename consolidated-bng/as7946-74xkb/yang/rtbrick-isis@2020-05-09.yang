submodule rtbrick-isis {
    yang-version 1.1;
    belongs-to rtbrick-config {
        prefix "config";
    }

    import rtbrick-isis-types {
        prefix "rtb-isis-types";
    }

    import rtbrick-types {
        prefix "rtb-types";
    }

    organization
      "Rtbrick";
    contact
      "Authors: Radhika talasu (radhika@rtbrick.com )
                Ankit Sinha (ankit@rtbrick.com)";

    description
        "This module describes a YANG model for ISIS protocol configuration.
        Albeit the model is inspired from openconfig-isis, it is tailored for
        Rtbrick This model supports the following ISIS configuration level
        hierarchy:
        ISIS
        +-> { global ISIS configuration}
            +-> levels +-> { level config}
            +-> interface +-> { interface config }
                +-> { levels config }
            +-> { authentication auth-config }
            +-> redistribute +-> { redistribute config }
            +-> address-family +-> { address-family config }";

    revision 2020-05-09 {
        description
          "Revamp isis yang file";
        reference "None";
    }

    grouping isis-bfd {
        description "ISIS BFD grouping";
        container bfd {
            presence bfd;
            description "ISIS BFD configuration";
            reference
            '{
                "table-getter": {
                    "library": "libisisyang.so",
                    "symbol": "isis_yang_get_interface_tbl_show_templ",
                    "type" :  "isis.interface.config.table",
                    "inherit-attribute":["interface"]
                }
            }';
            leaf admin-status {
                type rtb-types:boolean-type;
                description "BFD status";
                reference
                '{
                    "attribute-getter" : {
                        "attribute" : "bfd_status"
                    }
                }';
            }
            leaf profile {
                type string;
                description "BFD profile name";
                reference
                '{
                    "attribute-getter" : {
                        "attribute" : "profile",
                        "expansion-getter" : {
                            "package":"isis",
                            "method" : "isis_get_bfd_profile_name"
                        }
                    }
                }';
            }
        }
    }

    grouping isis-policy {
        description "Policy map name";
        leaf policy {
            type string;
            description "Policy map name";
            reference
            '{
                "attribute-getter" : {
                    "attribute" : "policy_name",
                     "expansion-getter" : {
                        "package":"isis",
                        "method" : "isis_policy_name_expander"
                      }
                }
            }';
        }
    }

    grouping interface-level-segment-routing {
        description "Grouping ISIS interface level segment routing configuration";
        container segment-routing {
            description "ISIS segment routing configuration for this interface";
            container ipv4 {
                description "ISIS IPv4 segment routing interface configuration";
                reference
                '{
                    "table-getter": {
                    "library": "libisisyang.so",
                    "symbol": "isis_yang_get_interface_tbl_show_templ",
                    "type" :  "isis.interface.config.table",
                    "inherit-attribute":[ "interface" ]
                    }
                }';
                leaf anycast-index {
                    type uint32;
                    description "Anycast index segment-ID";
                    reference
                    '{
                        "attribute-getter" : {
                            "attribute" : "ipv4_anycast_sid"
                        }
                    }';
                }

                leaf index {
                    type uint32;
                    must "../../../../segment-routing/srgb/base" {
                        error-message "configure SRGB base and range";
                    }
                    description "Index segment-ID";
                    reference
                    '{
                        "attribute-getter" : {
                            "attribute" : "ipv4_sid"
                        }
                    }';
                }
                must "not(index) or index <= ../../../segment-routing/srgb/range" {
                    error-message "Please enter a segment index within the configured SRGB range";
                }
            }
            container ipv6 {
                description "ISIS IPv6 segment routing interface configuration";
                reference
                '{
                    "table-getter": {
                    "library": "libisisyang.so",
                    "symbol": "isis_yang_get_interface_tbl_show_templ",
                    "type" :  "isis.interface.config.table",
                    "inherit-attribute":[ "interface" ]
                    }
                }';
                leaf anycast-index {
                    type uint32;
                    description "Authentication on hello packets";
                    reference
                    '{
                        "attribute-getter" : {
                            "attribute" : "ipv6_anycast_sid"
                        }
                    }';
                }

                leaf index {
                    type uint32;
                    must "../../../../segment-routing/srgb/base" {
                        error-message "configure SRGB base and range";
                    }
                    description "IPv6 index segment-id";
                    reference
                    '{
                        "attribute-getter" : {
                            "attribute" : "ipv6_sid"
                        }
                    }';
                }
                must "index <= ../../../segment-routing/srgb/range" {
                    error-message "Please enter a segment index within the configured SRGB range";
                }
            }
            container point-to-point {
                description "Grouping ISIS segment routing point-to-point interface configuration";
                reference
                '{
                    "table-getter": {
                    "library": "libisisyang.so",
                    "symbol": "isis_yang_get_interface_tbl_show_templ",
                    "type" :  "isis.interface.config.table",
                    "inherit-attribute":[ "interface" ]
                    }
                }';
                container ipv4 {
                    description "ISIS IPv4 segment routing interface configuration";
                    reference
                    '{
                        "table-getter": {
                        "library": "libisisyang.so",
                        "symbol": "isis_yang_get_interface_tbl_show_templ",
                        "type" :  "isis.interface.config.table",
                        "inherit-attribute":[ "interface" ]
                        }
                    }';
                    leaf adjacency-index {
                        type uint32;
                        description "Adjacency Segment Index";
                        reference
                        '{
                            "attribute-getter" : {
                                "attribute" : "ipv4_adjacency_sid"
                            }
                        }';
                    }
                }

                container ipv6 {
                    description "ISIS IPv6 segment routing interface configuration";
                    reference
                    '{
                        "table-getter": {
                        "library": "libisisyang.so",
                        "symbol": "isis_yang_get_interface_tbl_show_templ",
                        "type" :  "isis.interface.config.table",
                        "inherit-attribute":[ "interface" ]
                        }
                    }';
                    leaf adjacency-index {
                        type uint32;
                        description "Adjacency Segment Index";
                        reference
                        '{
                            "attribute-getter" : {
                                "attribute" : "ipv6_adjacency_sid"
                            }
                        }';
                    }
                }
            }
        }
    }
    // Configuration of ISIS
    grouping interface-level1 {
        description "Grouping ISIS interface configuration";
        container level-1 {
            description "ISIS interface level-1 configuration";
            reference
            '{
                "table-getter": {
                    "library": "libisisyang.so",
                    "symbol": "isis_yang_get_interface_tbl_show_templ",
                    "type" :  "isis.interface.config.table",
                    "inherit-attribute":[ "interface" ]
                }
            }';
            leaf snp-authentication {
                type rtb-types:enable-disable-type;
                description "Authentication on CSNP/PSNP packets";
                reference
                '{
                    "attribute-getter" : {
                        "attribute" : "level1_snp_authentication"
                    }
                }';
            }
            leaf hello-authentication {
                type rtb-types:enable-disable-type;
                description "Authentication on hello packets";
                reference
                '{
                    "attribute-getter" : {
                        "attribute" : "level1_hello_authentication"
                    }
                }';
            }
            leaf metric
            {
                type rtb-isis-types:protocol-metric;
                description
                    "Level-1 metric on an interface, default 1000000";
                reference
                '{
                    "attribute-getter" : {
                        "attribute" : "level1_metric"
                    }
                }';
            }
            leaf adjacency-disable
            {
                type rtb-types:boolean-type;
                description
                    "Level-1 adjacency on an interface, default false";
                reference
                '{
                    "attribute-getter" : {
                        "attribute" : "level1_disable"
                    }
                }';
            }
        }
    }

    grouping interface-level2 {
        description "Grouping ISIS interface level-2 configuration";
        container level-2 {
            description "ISIS interface level-2 configuration";
            reference
            '{
                "table-getter": {
                    "library": "libisisyang.so",
                    "symbol": "isis_yang_get_interface_tbl_show_templ",
                    "type" :  "isis.interface.config.table",
                    "inherit-attribute":[ "interface" ]
                }
            }';
            leaf snp-authentication {
                type rtb-types:enable-disable-type;
                description "Authentication on CSNP/PSNP packets";
                reference
                '{
                    "attribute-getter" : {
                        "attribute" : "level2_snp_authentication"
                    }
                }';
            }
            leaf hello-authentication {
                type rtb-types:enable-disable-type;
                description "Authentication on hello packets";
                reference
                '{
                    "attribute-getter" : {
                        "attribute" : "level2_hello_authentication"
                    }
                }';
            }
            leaf metric
            {
                type rtb-isis-types:protocol-metric;
                description
                    "Level-2 metric on an interface, default 1000000";
                reference
                '{
                    "attribute-getter" : {
                        "attribute" : "level2_metric"
                    }
                }';
            }
            leaf adjacency-disable
            {
                type rtb-types:boolean-type;
                description
                    "Level-2 adjacency on interface, default false";
                reference
                '{
                    "attribute-getter" : {
                        "attribute" : "level2_disable"
                    }
                }';
            }
        }
    }

    grouping interface-level {
        description "Grouping of ISIS interface authentication configuration";
        uses interface-level1;
        uses interface-level2;
    }

    grouping isis-level1-redistribute {
        description "Grouping of ISIS redistribution configuration";
        list redistribute{
            key "source";
            description "Redistribution configuration";
            reference
            '{
                "table-getter": {
                    "library": "libisisyang.so",
                    "symbol": "isis_yang_get_redistribute_tbl_show_templ",
                    "type" :  "isis.protocolinfra.redistribution_table",
                    "inherit-attribute":["instance_name","afi", "safi" ],
                    "default-attribute": [ { "dest_sub_type": "level-1" }, { "dest": "isis"} ]
                }
            }';
            leaf source {
                type rtb-isis-types:rib-source;
                description "Source protocol";
                reference
                '{
                    "attribute-getter" : {
                        "attribute" : "source"
                    }
                }';
            }
            leaf metric {
                type rtb-isis-types:protocol-metric;
                description "Protocol metric";
                reference
                '{
                    "attribute-getter" : {
                        "attribute" : "metric"
                    }
                }';
            }
            uses isis-policy;
        }
    }

    grouping isis-level2-redistribute {
        description "Grouping of ISIS redistribution configuration";
        list redistribute{
            key "source";
            description "Redistribution configuration";
            reference
            '{
                "table-getter": {
                    "library": "libisisyang.so",
                    "symbol": "isis_yang_get_redistribute_tbl_show_templ",
                    "type" :  "isis.protocolinfra.redistribution_table",
                    "inherit-attribute":["instance_name","afi", "safi" ],
                    "default-attribute": [ { "dest_sub_type": "level-2" }, { "dest": "isis"} ]
                }
            }';
            leaf source {
                type rtb-isis-types:rib-source;
                description "Source protocol";
                reference
                '{
                    "attribute-getter" : {
                        "attribute" : "source"
                    }
                }';
            }
            leaf metric {
                type rtb-isis-types:protocol-metric;
                description "Protocol metric";
                reference
                '{
                    "attribute-getter" : {
                        "attribute" : "metric"
                    }
                }';
            }
            uses isis-policy;
        }
    }

    grouping isis-level1-afi-safi {
        description "ISIS afi safi group";
        list address-family{
            key "afi safi";
            description "Address family configuration";
            reference
            '{
                "table-getter": {
                    "library": "libisisyang.so",
                    "symbol": "isis_yang_get_global_afi_tbl_show_templ",
                    "type" :  "isis.afi_safi_config_table",
                    "default-attribute": [ { "dest_sub_type": "level-1" } ]
                }
            }';
            leaf afi {
                type rtb-isis-types:afi;
                description "Type afi";
                reference
                '{
                    "attribute-getter" : {
                        "attribute" : "afi"
                    }
                }';
            }
            leaf safi {
                type rtb-isis-types:safi;
                description "Type safi";
                reference
                '{
                    "attribute-getter" : {
                        "attribute" : "safi"
                    }
                }';
            }
            uses isis-level1-redistribute;
        }
    }

    grouping isis-level2-afi-safi {
        description "ISIS afi safi group";
        list address-family{
            key "afi safi";
            description "Address family configuration";
            reference
            '{
                "table-getter": {
                    "library": "libisisyang.so",
                    "symbol": "isis_yang_get_global_afi_tbl_show_templ",
                    "type" :  "isis.afi_safi_config_table",
                    "default-attribute": [ { "dest_sub_type": "level-2" } ]
                }
            }';
            leaf afi {
                type rtb-isis-types:afi;
                description "Type afi";
                reference
                '{
                    "attribute-getter" : {
                        "attribute" : "afi"
                    }
                }';
            }
            leaf safi {
                type rtb-isis-types:safi;
                description "Type safi";
                reference
                '{
                    "attribute-getter" : {
                        "attribute" : "safi"
                    }
                }';
            }
            uses isis-level2-redistribute;
        }
    }

    grouping isis-segment-routing {
        description "ISIS Segment Routing group";
        container segment-routing {
            description "ISIS Segment Routing configuration";
            reference
            '{
                "table-getter": {
                    "table-name": "global.isis.instance.config",
                    "type" :  "isis.config.table",
                    "inherit-attribute":["instance_name"]
                }
            }';
            container srlb {
                description "Segment Routing Local Block";
                reference
                '{
                    "table-getter": {
                        "table-name": "global.isis.instance.config",
                        "type" :  "isis.config.table",
                        "inherit-attribute":["instance_name"]
                    }
                }';
                leaf base
                {
                    type uint32 {
                        range "16 .. 1048575";
                    }
                    must "../range" {
                        error-message "configure/un-configure SRGB base and range";
                    }
                    description "Base label for Segment routing Local Block";
                    reference
                    '{
                        "attribute-getter" : {
                            "attribute" : "srlb_base"
                        }
                    }';
                }

                leaf range
                {
                    type uint32;
                    must "../base" {
                        error-message "configure/un-configure SRGB base and range";
                    }
                    description "ISIS system range of labels from the Segment routing Local Block base label ";
                    reference
                    '{
                        "attribute-getter" : {
                        "attribute" : "srlb_range"
                        }
                    }';
                }
            }

            container srgb {
                description "Segment Routing Global Block";
                reference
                '{
                    "table-getter": {
                        "table-name": "global.isis.instance.config",
                        "type" :  "isis.config.table",
                        "inherit-attribute":["instance_name"]
                    }
                }';

                leaf base
                {
                    type uint32 {
                        range "16 .. 1048575";
                    }
                    description "Base label for Segment Routing Global Block";
                    reference
                    '{
                        "attribute-getter" : {
                            "attribute" : "srgb_base"
                        }
                    }';
                }

                leaf range
                {
                    type uint32;
                    description "ISIS system range of labels from the Segment Routing Global Block base label ";
                    reference
                    '{
                        "attribute-getter" : {
                        "attribute" : "srgb_range"
                        }
                    }';
                }
            }
        }
    }

    grouping isis-interface {
        description "ISIS interface group";
        list interface {
            key "name";
            description "ISIS interface configuration";
            reference
            '{
                "table-getter": {
                    "library": "libisisyang.so",
                    "symbol": "isis_yang_get_interface_tbl_show_templ",
                    "type" :  "isis.interface.config.table"
                }
            }';
            leaf name {
                type string {
                    length "1..64";
                }
                description
                    "ISIS interface";
                reference
                '{
                    "attribute-getter" : {
                        "attribute" : "interface",
                         "expansion-getter" : {
                            "package":"isis",
                            "method" : "isis_ifm_interface_logical_name_expander_without_recyc"
                          }

                    }
                }';
            }
            leaf flood-filter {
                type string;
                description
                    "ISIS flood filter name";
                reference
                '{
                    "attribute-getter" : {
                        "attribute" : "flood_filter_name"
                    }
                }';
            }
            leaf type
            {
                type rtb-isis-types:isis-interface;
                description
                    "ISIS system interface Type";
                reference
                '{
                    "attribute-getter" : {
                        "attribute" : "interface_type"
                    }
                }';
            }
            leaf lsp-interval
            {
                type uint32 {
                    range "1 .. 1000";
                }
                units   "milliseconds";
                description
                    "ISIS system interface LSP interval, default 100";
                reference
                '{
                    "attribute-getter" : {
                        "attribute" : "lsp_interval"
                    }
                }';
            }
            leaf passive
            {
                type rtb-types:boolean-type;
                description
                    "Enable interface in passive mode, default false";
                reference
                '{
                    "attribute-getter" : {
                        "attribute" : "is_passive"
                    }
                }';
            }
            leaf system-id
            {
                type rtb-isis-types:system-id;
                description
                    "Interface level system id";
                reference
                '{
                    "attribute-getter" : {
                        "attribute" : "local_system_id"
                    }
                }';
            }
            leaf ldp-synchronization
            {
                type rtb-types:enable-disable-type;
                description
                    "Enable LDP IGP Synchronization, default disable";
                reference
                '{
                    "attribute-getter" : {
                        "attribute" : "ldp_synchronization"
                    }
                }';
            }
            uses interface-level-segment-routing;
            uses interface-level;
            uses isis-bfd;
        }
    }

    grouping isis-level1-authentication {
        description "ISIS level-1 authentication configuration";
        container level-1 {
            description "ISIS level-1 authentication configuration";
            reference
            '{
                "table-getter": {
                    "table-name": "global.isis.instance.config",
                    "type" :  "isis.config.table",
                    "inherit-attribute":["instance_name"]
                }
            }';
            leaf type {
                type rtb-isis-types:auth-type;
                description
                    "Authentication type";
                reference
                '{
                    "attribute-getter" : {
                        "attribute" : "level1_authentication_type"
                    }
                }';
            }
            leaf key1-plain-text {
                type string;
                description
                    "Authentication key";
                reference
                '{
                    "attribute-getter" : {
                        "attribute" : "level1_authentication_key",
			"plain-text-password" : true,
			"secret-text-leaf-name" : "key1-encrypted-text"
                    }
                }';
            }
            leaf key1-encrypted-text {
                type string;
                description
                    "Authentication key1 encrypted";
                reference
                '{
                    "attribute-getter" : {
                        "attribute" : "level1_authentication_key"
                    }
                }';
            }
            leaf key2-plain-text {
                type string;
                description
                    "Authentication key2";
                reference
                '{
                    "attribute-getter" : {
                        "attribute" : "level1_authentication_key2",
			"plain-text-password" : true,
			"secret-text-leaf-name" : "key2-encrypted-text"
                    }
                }';
            }
            leaf key2-encrypted-text {
                type string;
                description
                    "Authentication key 2 encrypted";
                reference
                '{
                    "attribute-getter" : {
                        "attribute" : "level1_authentication_key2"
                    }
                }';
            }
            leaf key-id1 {
                type uint8;
                description
                    "Authentication key-id1";
                reference
                '{
                    "attribute-getter" : {
                        "attribute" : "level1_authentication_key_id"
                    }
                }';
            }
            leaf key-id2 {
                type uint8;
                description
                    "Authentication key-id2";
                reference
                '{
                    "attribute-getter" : {
                        "attribute" : "level1_authentication_key_id2"
                    }
                }';
            }
            leaf check {
                type rtb-types:enable-disable-type;
                description "Authentication validation for all isis packets";
                reference
                '{
                    "attribute-getter" : {
                        "attribute" : "level1_authentication_check"
                    }
                }';
            }
        }
    }

    grouping isis-level2-authentication {
        description "ISIS level-2 authentication configuration";
        container level-2 {
            description "ISIS level-2 authentication configuration";
            reference
            '{
                "table-getter": {
                    "table-name": "global.isis.instance.config",
                    "type" :  "isis.config.table",
                    "inherit-attribute":["instance_name"]
                }
            }';
            leaf type {
                type rtb-isis-types:auth-type;
                description
                    "Authentication type";
                reference
                '{
                    "attribute-getter" : {
                        "attribute" : "level2_authentication_type"
                    }
                }';
            }
            leaf key1-plain-text {
                type string;
                description
                    "Authentication key1";
                reference
                '{
                    "attribute-getter" : {
                        "attribute" : "level2_authentication_key",
			"plain-text-password" : true,
			"secret-text-leaf-name" : "key1-encrypted-text"
                    }
                }';
            }
            leaf key1-encrypted-text {
                type string;
                description
                    "Authentication key1 encrypted";
                reference
                '{
                    "attribute-getter" : {
                        "attribute" : "level2_authentication_key"
                    }
                }';
            }
            leaf key2-plain-text {
                type string;
                description
                    "Authentication key2";
                reference
                '{
                    "attribute-getter" : {
                        "attribute" : "level2_authentication_key2",
                        "plain-text-password" : true,
                        "secret-text-leaf-name" : "key2-encrypted-text"
                    }
                }';
            }
            leaf key2-encrypted-text {
                type string;
                description
                    "Authentication key2 encrypted";
                reference
                '{
                    "attribute-getter" : {
                        "attribute" : "level2_authentication_key2"
                    }
                }';
            }
            leaf key-id1 {
                type uint8;
                description
                    "Authentication key-id 1";
                reference
                '{
                    "attribute-getter" : {
                        "attribute" : "level2_authentication_key_id"
                    }
                }';
            }
            leaf key-id2 {
                type uint8;
                description
                    "Authentication key-id 2";
                reference
                '{
                    "attribute-getter" : {
                        "attribute" : "level2_authentication_key_id2"
                    }
                }';
            }
            leaf check {
                type rtb-types:enable-disable-type;
                description "Authentication validation for all isis packets";
                reference
                '{
                    "attribute-getter" : {
                        "attribute" : "level2_authentication_check"
                    }
                }';
            }
        }
    }

    grouping isis-authentication {
        description "Authentication configurations";
        container authentication {
            description "ISIS authentication configuration";
            uses isis-level1-authentication;
            uses isis-level2-authentication;
        }
    }


    grouping isis-global-top  {
        description "ISIS configuration";
        container isis {
            description "Global flood-filter configuration";
            list flood-filter{
                key "filter-name ordinal";
                description "Global flood-filter configuration";
                reference
                '{
                    "table-getter": {
                        "table-name": "global.isis.flood-filter.config",
                        "type" :  "isis.flood.filter.table"
                    }
                }';
                leaf filter-name {
                    type string;
                    description "Name of the filter";
                    reference
                    '{
                        "attribute-getter" : {
                            "attribute" : "flood_filter_name"
                        }
                    }';
                }
                leaf ordinal {
                    type uint8;
                    description "Ordinal number";
                    reference
                    '{
                        "attribute-getter" : {
                            "attribute" : "ordinal"
                        }
                    }';
                }
                leaf ordinal-name {
                    type string;
                    description "Name of the ordinal";
                    reference
                    '{
                        "attribute-getter" : {
                            "attribute" : "ordinal_name"
                        }
                    }';
                }
                leaf system-id {
                    type rtb-isis-types:system-id;
                    description "IS-IS instance system-id";
                    reference
                    '{
                        "attribute-getter" : {
                            "attribute" : "match_sysid"
                        }
                    }';
                }
                leaf system-id-mask {
                    type rtb-isis-types:system-id;
                    description "System ID mask on which the filter should match";
                    reference
                    '{
                        "attribute-getter" : {
                            "attribute" : "match_sysid_mask"
                        }
                    }';
                }
                leaf action {
                    type rtb-isis-types:flood-filter-action;
                    description "The flooding filter action";
                    reference
                    '{
                        "attribute-getter" : {
                            "attribute" : "action"
                        }
                    }';
                }
            }
        }
    }

    grouping isis-level-1 {
        description
        "This grouping define isis level-1 related configuration";
        container level-1 {
            description "Protocol ISIS level-1 configuration";
            uses isis-level1-afi-safi;
        }
    }

    grouping isis-level-2 {
        description
        "This grouping define isis level-2 related configuration";
        container level-2 {
            description "Protocol ISIS level-2 configuration";
            uses isis-level2-afi-safi;
        }
    }

    grouping isis-top {
        description
        "This grouping define top-level ISIS model data.";

        container isis {
            description "Protocol ISIS configuration";
            reference
            '{
                "table-getter": {
                    "table-name": "global.isis.instance.config",
                    "type" :  "isis.config.table",
                    "inherit-attribute":["instance_name"]
                }
            }';
            leaf system-id
            {
                type rtb-isis-types:system-id;
                description
                    "ISIS neighbor system-id";
                reference
                '{
                    "attribute-getter" : {
                        "attribute" : "system_id"
                    }
                }';
            }
            leaf overload
            {
                type rtb-types:boolean-type;
                description
                    "When set to true, IS-IS overload bit is set, default false";
                reference
                '{
                    "attribute-getter" : {
                        "attribute" : "overload"
                    }
                }';
            }
            leaf holding-time
            {
                type uint8 {
                    range "3 .. 180";
                }
                units "seconds";
                description
                    "ISIS neighbor hold interval in range <3,180> seconds, default 30s";
                reference
                '{
                    "attribute-getter" : {
                        "attribute" : "holding_time"
                    }
                }';
            }
            leaf multipath
            {
                type uint16;
                description
                    "Load sharing among multiple ISIS paths, default 256";
                reference
                '{
                    "attribute-getter" : {
                        "attribute" : "multipath"
                    }
                }';
            }
            leaf-list area
            {
                type rtb-isis-types:iso-prefix;
                max-elements 3;
                description
                    "ISIS area-address";
                reference
                '{
                    "attribute-getter" : {
                        "attribute" : "area"
                    }
                }';
            }

            leaf hostname
            {
                type string {
                   length "1..255";
                }
                description
                    "ISIS system host name ";
                reference
                '{
                    "attribute-getter" : {
                        "attribute" : "hostname"
                    }
                }';
            }
            leaf lsp-lifetime
            {
                type uint16 {
                    range "317 .. 65535";
                }
                units "seconds";

                description
                    "ISIS link-state PDUs maximum lifetime, default 65535s";
                reference
                '{
                    "attribute-getter" : {
                        "attribute" : "lsp_lifetime_interval"
                    }
                }';
            }

            leaf ignore-attached-bit
            {
                type rtb-types:boolean-type;
                description
                    "When set to true, IS-IS will ignore received attached bit in L1 LSP, default false";
                reference
                '{
                    "attribute-getter" : {
                        "attribute" : "ignore_attached_bit"
                    }
                }';
            }

            leaf no-mpls-transit-path
            {
                type rtb-types:boolean-type;
                description
                    "When set to true, IS-IS will not install segment routing transit path, default false";
                reference
                '{
                    "attribute-getter" : {
                        "attribute" : "no_mpls_transit_path"
                    }
                }';
            }

            leaf router-id
            {
                type rtb-types:router-id-type;
                description
                    "ISIS router identifier (ipv4 format: A.B.C.D)";
                reference
                '{
                    "attribute-getter" : {
                        "attribute" : "router_id"
                    }
                }';
            }

            leaf ipv6-disable
            {
                type rtb-types:boolean-type;
                description
                    "When set to true, IS-IS will not advertise or process ipv6 routes, default false";
                reference
                '{
                    "attribute-getter" : {
                        "attribute" : "ipv6_disable"
                    }
                }';
            }

            container level1-to-level2 {
                description "Level-1 to Level-2";
                reference
                '{
                    "table-getter": {
                        "table-name": "global.isis.instance.config",
                        "type" :  "isis.config.table",
                        "inherit-attribute":["instance_name"]
                    }
                }';
                leaf route-leak
                {
                    type rtb-types:enable-disable-type;
                    description
                        "When set to disable, IS-IS will not leak routes from Level-1 to Level-2";
                    reference
                    '{
                        "attribute-getter" : {
                            "attribute" : "level1_to_level2_route_leak"
                        }
                    }';
                }
            }
            uses isis-authentication;
            uses isis-segment-routing;
            uses isis-interface;
            //uses isis-afi-safi;
            uses isis-level-1;
            uses isis-level-2;
        }
    }
}
