submodule rtbrick-access-user-profile {
    yang-version 1.1;
    belongs-to rtbrick-config {
        prefix config;
    }

    organization
      "Rtbrick";
    contact
      "Authors: Deeksha Bhandary (deeksha@rtbrick.com)";

    description
        "This sub module contains the top level configurations of dummy access-user-profile config to help rtbrick roles.
  	This must be pre-date the older package";

    revision 2020-01-01 {
        description
          "Dummy access-user-profile file";
    }

    grouping access-user-profile {
        description "Dummy global access-user-profile top level config";
    }
}
