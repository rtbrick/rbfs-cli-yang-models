submodule rtbrick-address-translation {

    yang-version 1.1;

    belongs-to rtbrick-config {
        prefix config;
    }

    import rtbrick-types {
        prefix "rtb-types";
    }

    organization
      "RtBrick";
    contact
      "Authors: Mahendra Singh Negi (mahendra@rtbrick.com)
                Jeevan Samrudh L H  (jeevan@rtbrick.com)";
    description
      "This sub-module contains yang structure for
       Address Translation.";
    revision 2023-08-06 {
        description "First revision";
        reference "None";
    }
    typedef type-ipproto-address-translation {
        type enumeration {
            enum "tcp" {
                value 6;
                description "TCP";
            }
            enum "udp" {
                value 17;
                description "UDP";
            }
        }
        description "IP protocol type for NAT";
    }
    typedef type-port-block-size {
        type enumeration {
            enum "64" {
                value 64;
                description "64 Ports";
            }
            enum "128" {
                value 128;
                description "128 Ports";
            }
            enum "256" {
                value 256;
                description "256 Ports";
            }
            enum "512" {
                value 512;
                description "512 Ports";
            }
            enum "1024" {
                value 1024;
                description "1024 Ports";
            }
            enum "2048" {
                value 2048;
                description "2048 Ports";
            }
        }
        description "NAT supported Ports per block";
    }
    typedef type-max-rules {
        type enumeration {
            enum "64" {
                value 64;
                description "64 Rules";
            }
            enum "128" {
                value 128;
                description "128 Rules";
            }
            enum "256" {
                value 256;
                description "256 Rules";
            }
            enum "512" {
                value 512;
                description "512 Rules";
            }
            enum "1024" {
                value 1024;
                description "1024 Rules";
            }
            enum "2048" {
                value 2048;
                description "2048 Rules";
            }
        }
        description "NAT supported Ports per block";
    }
    typedef type-address-translation-string {
        type string {
            length "1..64";
            pattern
                '^[_0-9a-zA-Z].*$';
        }
        description "Acceptable string type for address-translation";
    }
    grouping address-translation-pool-top {
        description "Top-level grouping for address translation pool";

        list pool {
            key "pool-name";
            description "Global nat pool configuration";
            reference
            '{
                "table-getter": {
                    "table-name" : "global.nat.pool.config",
                    "type"    : "nat_pool_config_table"
                }
            }';
            leaf pool-name {
                type string {
                    length "1 .. 64";
                }
                description "Name of the address pool";
                reference
                '{
                    "attribute-getter" : {
                        "attribute" : "pool_name"
                    }
                }';
            }
            leaf next-pool-name {
                type string {
                    length "1 .. 64";
                }
                must '. = ../../pool/pool-name' {
                        error-message "Pool attached as a next pool is not configured";
                }
                description "Name of the next address pool to be used if full";
                reference
                '{
                    "attribute-getter" : {
                        "attribute" : "next_pool_name",
                        "expansion-getter" : {
                            "package":"nat",
                            "method" :"nat_pool_name_expander"
                        }
                    }
                }';
            }
            leaf port-block-size {
                type type-port-block-size;
                description "Number of Ports per block";
                default "128";
                reference
                '{
                    "attribute-getter" : {
                        "attribute" : "port_block_size"
                    }
                }';
            }
            container ipv4-address {
                description "IPv4 address pool configuration";
                reference
                '{
                    "table-getter": {
                        "type"    : "nat_pool_config_table",
                        "table-name" : "global.nat.pool.config",
                        "inherit-attribute": ["pool_name"]
                    }
                }';
                leaf low {
                    type rtb-types:non-reserved-ipv4-address;
                    mandatory true;
                    must '../high' {
                        error-message "Maximum IP Address of the pool should be configured";
                    }
                    description "Lowest IPv4 address";
                    reference
                    '{
                        "attribute-getter" : {
                            "attribute" : "ipv4_range_low"
                        }
                    }';
                }
                leaf high {
                    type rtb-types:non-reserved-ipv4-address;
                    mandatory true;
                    must '../low' {
                        error-message "Minimum IP Address of the pool should be configured";
                    }
                    description "Highest IPv4 address";
                    reference
                    '{
                        "attribute-getter" : {
                            "attribute" : "ipv4_range_high"
                        }
                    }';
                }
            }
        }
    }
    grouping address-translation-profile-protocol {
        description "Grouping for address translation profile protocol";
        container ip-protocol {
            description "Configuration parameters for IP protocol";
            container tcp {
                description "Configuration parameters for TCP protocol";
                reference
                '{
                    "table-getter": {
                        "table-name" : "global.nat.profile.config",
                        "type"    : "nat_profile_config_table",
                        "inherit-attribute" : [ "profile_name" ]
                    }
                }';
                leaf ageing-timeout {
                    type uint32;
                    description "NAT inactivity timeout";
                    default "600";
                    reference
                    '{
                        "attribute-getter" : {
                            "attribute" : "ageing_timeout_tcp"
                        }
                    }';
                }
            }
            container udp {
                description "Configuration parameters for UDP protocol";
                reference
                '{
                    "table-getter": {
                        "table-name" : "global.nat.profile.config",
                        "type"    : "nat_profile_config_table",
                        "inherit-attribute" : [ "profile_name" ]
                    }
                }';
                leaf ageing-timeout {
                    type uint32;
                    description "NAT inactivity timeout";
                    default "300";
                    reference
                    '{
                        "attribute-getter" : {
                            "attribute" : "ageing_timeout_udp"
                        }
                    }';
                }
            }
            container other {
                description "Configuration parameters for all the other protocols";
                reference
                '{
                    "table-getter": {
                        "table-name" : "global.nat.profile.config",
                        "type"    : "nat_profile_config_table",
                        "inherit-attribute" : [ "profile_name" ]
                    }
                }';
                leaf ageing-timeout {
                    type uint32;
                    description "NAT inactivity timeout";
                    default "300";
                    reference
                    '{
                        "attribute-getter" : {
                            "attribute" : "ageing_timeout_all"
                        }
                    }';
                }
            }
        }
    }
    grouping address-translation-profile-top {
        description "Top-level grouping for address translation profile";

        list profile {
            key "profile";
            description "Global nat profile configuration";
            reference
            '{
                "table-getter": {
                    "table-name" : "global.nat.profile.config",
                    "type"    : "nat_profile_config_table"
                }
            }';
            leaf profile {
                type string {
                    length "1 .. 64";
                }
                description "Name of the NAT profile";
                reference
                '{
                    "attribute-getter" : {
                        "attribute" : "profile_name"
                    }
                }';
            }
            leaf instance {
                type string {
                    length "1 .. 64";
                }
                mandatory true;
                must 'count(../../profile[instance=current()])=1' {
                    error-message "Only one NAT Profile can be configured per instance";
                }
                description
                    "Configuring NAT for an instance";
                reference
                '{
                    "attribute-getter" : {
                        "attribute" : "instance",
                        "expansion-getter" : {
                            "package":"nat",
                            "method" :"nat_instance_name_expander"
                        }
                    }
                }';
            }
            leaf pool {
                type string {
                    length "1 .. 64";
                }
                mandatory true;
                must '. = ../../pool/pool-name' {
                    error-message "Pool attached to NAT profile is not configured";
                }
                description "Name of the address pool";
                reference
                '{
                    "attribute-getter" : {
                        "attribute" : "pool_name",
                        "expansion-getter" : {
                            "package":"nat",
                            "method" :"nat_pool_name_expander"
                        }
                    }
                }';
            }
            leaf max-rules {
                type type-max-rules;
                default "128";
                description
                    "Configure Maximum translations for an interface";
                reference
                '{
                    "attribute-getter" : {
                        "attribute" : "maximum_rules"
                    }
                }';
            }
            leaf deterministic {
                type rtb-types:boolean-true;
                description
                    "Configure to restrict users to have a single public IP";
                reference
                '{
                    "attribute-getter" : {
                        "attribute" : "deterministic",
                    }
                }';
            }
            uses address-translation-profile-protocol;
        }
    }
    grouping address-translation-local-ipv4 {
        description
            "Configuring NAT local address and port";
        container local {
            description
                "Configuration parameters for local IPv4 address";
            reference
            '{
                "table-getter": {
                    "table-name" : "global.nat.rule.config",
                    "type"    : "nat_rule_config_table",
                    "inherit-attribute" : [ "rule", "ordinal" ]
                }
            }';
            leaf ipv4-address {
                type rtb-types:non-reserved-ipv4-address;
                mandatory true;
                description
                    "Configuring ipv4 local address";
                reference
                '{
                    "attribute-getter" : {
                        "attribute" : "local_address4"
                    }
                }';
            }
            leaf port {
                type uint16 {
                    range "1024 .. 65535";
                }
                mandatory true;
                description
                    "Configuring l4 port";
                reference
                '{
                    "attribute-getter" : {
                        "attribute" : "local_port"
                    }
                }';
            }
        }
    }
    grouping address-translation-public-ipv4 {
        description
            "Configuring NAT public address and port";
        container public {
            description
                "Configuration parameters for public IPv4 address";
            reference
            '{
                "table-getter": {
                    "table-name" : "global.nat.rule.config",
                    "type"    : "nat_rule_config_table",
                    "inherit-attribute" : [ "rule", "ordinal" ]
                }
            }';
            leaf ipv4-address {
                type rtb-types:non-reserved-ipv4-address;
                mandatory true;
                description
                    "Configuring ipv4 public address";
                reference
                '{
                    "attribute-getter" : {
                        "attribute" : "public_address4"
                    }
                }';
            }
            leaf port {
                type uint16 {
                    range "1024 .. 65535";
                }
                mandatory true;
                description
                    "Configuring public l4 port";
                reference
                '{
                    "attribute-getter" : {
                        "attribute" : "public_port"
                    }
                }';
            }
        }
    }
    grouping address-translation-rule-top {
        description
            "Top-level grouping for address translation rule";
        list rule {
            key "rule-name";
            description
                "Configuration parameters for address-translation rule";
            reference
                '{
                    "table-getter": {
                        "table-name" : "global.nat.rule.mode.config",
                        "type"    : "nat_rule_mode_config_table"
                    }
                }';
            leaf rule-name {
                type type-address-translation-string;
                description
                    "Configure address-translatoin rule name";
                reference
                    '{
                        "attribute-getter" : {
                            "attribute" : "rule"
                        }
                    }';
            }
            list ordinal {
                key "ordinal-value";
                description
                    "Configuration parameters relating acl ordinal";
                reference
                    '{
                        "table-getter": {
                            "table-name" : "global.nat.rule.config",
                            "type"    : "nat_rule_config_table",
                            "inherit-attribute" : [ "rule" ]
                        }
                    }';
                leaf ordinal-value {
                    type uint32 {
                        range "0 .. 200000";
                    }
                    description
                        "Configure ordinal value";
                    reference
                        '{
                            "attribute-getter" : {
                                "attribute" : "ordinal"
                            }
                        }';
                }
                uses address-translation-local-ipv4;
                uses address-translation-public-ipv4;
                leaf ip-protocol {
                    type type-ipproto-address-translation;
                    description
                        "Configuring IP protocol value";
                    reference
                    '{
                        "attribute-getter" : {
                            "attribute" : "protocol"
                        }
                    }';
                }
                leaf instance {
                    type string {
                        length "1 .. 64";
                    }
                    description
                        "Configuring NAT for an instance";
                    reference
                    '{
                        "attribute-getter" : {
                            "attribute" : "instance",
                            "expansion-getter" : {
                                "package":"nat",
                                "method" :"nat_instance_name_expander"
                            }
                        }
                    }';
                }
            }
        }
     }
    grouping address-translation-top {
        description
            "Top-level grouping for address-translation model";
        container address-translation {
            description
                "Top-level container for address-translation data";
            uses address-translation-pool-top;
            uses address-translation-profile-top;
            uses address-translation-rule-top;
        } //container address-translation
    } //grouping address-translation-top
}
