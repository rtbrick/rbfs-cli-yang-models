submodule rtbrick-access-access-profile {

    yang-version 1.1;                                                                

    belongs-to rtbrick-config {
        prefix config;
    }

    import ietf-inet-types {
        prefix "inet";
        reference "RFC 6991";
    }
    import rtbrick-types {
        prefix "rtb-types";
    }
    import clixon-autocli{
        prefix autocli;
    }
    include rtbrick-forwarding-options;
    organization
      "RtBrick";
    contact
      "Authors: Vyshakh Krishnan (vyshakh@rtbrick.com)";
    description
      "This sub-module contains yang structure for
       access profile configuration.";
    revision 2020-07-25 {
        description "First revision";
        reference "None";
    }

    typedef authentication-protocol {
        type enumeration {
            enum PAP {
                value "1";
            }
            enum CHAP {
                value "2";
            }
            enum PAP_CHAP {
                value "3";
            }
            enum CHAP_PAP {
                value "4";
            }
        }
        description "Authentication protocol";
    }

    typedef dhcp-mode {
        type enumeration {
            enum server {
                value "0";
            }
            enum relay {
                value "1";
            }
        }
        description "DHCP mode";
    }

    typedef proxy-arp-mode {
        type enumeration {
            enum disabled {
                value "0";
            }
            enum subscriber {
                value "1";
            }
            enum any {
                value "2";
            }
        }
        description "Proxy ARP mode";
    }

    grouping access-access-profile {
        description "Global access profile configuration";

        list access-profile {
            key "profile-name";
            description "Global access profile configuration";
            reference
            '{
                "table-getter": {
                    "table-name" : "global.access.profile.config",
                    "type"    : "access_profile_config_table"
                }
            }';
            leaf profile-name {
                type string {
                    length "1..64";
                }
                description "Name of the access profile";
                reference
                '{
                    "attribute-getter" : {
                        "attribute" : "access_profile_name"
                    }
                }';
            }
            leaf instance {
                type string {
                    length "1..64";
                }
                description "Instance name";
                reference
                '{
                    "attribute-getter" : {
                        "attribute" : "instance_name",
                        "expansion-getter" : {
                            "package":"subsMgmt",
                            "method" :"access_instance_name_expander"
                        }
                    }
                }';
            } 
            container protocol {
                description "Protocol configuration";
                container pppoe {
                    description "Protocol PPPoE";
                    reference
                    '{
                        "table-getter": {
                            "table-name" : "global.access.profile.config",
                            "type"    : "access_profile_config_table",
                            "inherit-attribute": ["access_profile_name"]
                        }
                    }';
                    leaf enable {
                        type rtb-types:boolean-type;
                        description "Enable PPPoE";
                        reference
                        '{
                            "attribute-getter" : {
                                "attribute" : "pppoe_enabled"
                            }
                        }';
                    }
                    container session-protection {
                        description "PPPoE session protection";
                        reference
                        '{
                            "table-getter": {
                                "table-name" : "global.access.profile.config",
                                "type"    : "access_profile_config_table",
                                "inherit-attribute": ["access_profile_name"]
                            }
                        }';
                        leaf enable {
                            type rtb-types:boolean-type;
                            description "Enable PPPoE session protection";
                            reference
                            '{
                                "attribute-getter" : {
                                    "attribute" : "pppoe_session_protection_enabled"
                                }
                            }';
                        }
                        leaf min-uptime {
                            type uint16 { 
                                range "1..65535";
                            }
                            description "Session protection minimum uptime in seconds";
                            reference
                            '{
                                "attribute-getter" : {
                                    "attribute" : "pppoe_session_protection_min_uptime"
                                }
                            }';
                        }
                        leaf min-lockout {
                            type uint8 { 
                                range "1..255";
                            }
                            description "Session protection minimum lockout time in seconds";
                            reference
                            '{
                                "attribute-getter" : {
                                    "attribute" : "pppoe_session_protection_min_lockout"
                                }
                            }';
                        }
                        leaf max-lockout {
                            type uint16 { 
                                range "1..65535";
                            }
                            description "Session protection maximum lockout time in seconds";
                            reference
                            '{
                                "attribute-getter" : {
                                    "attribute" : "pppoe_session_protection_max_lockout"
                                }
                            }';
                        }
                    }
                    leaf max-outstanding {
                        type uint16 { 
                            range "1..65535";
                        }
                        description "Maximum outstanding PPPoE sessions";
                        reference
                        '{
                            "attribute-getter" : {
                                "attribute" : "pppoe_outstanding_limit"
                            }
                        }';
                    }
                }
                container ppp {
                    description "Protocol PPP";
                    container lcp {
                        description "Protocol LCP";
                        reference
                        '{
                            "table-getter": {
                                "table-name" : "global.access.profile.config",
                                "type"    : "access_profile_config_table",
                                "inherit-attribute": ["access_profile_name"]
                            }
                        }';
                        leaf authentication-protocol {
                            type authentication-protocol;
                            description "Authentication protocol";
                            reference
                            '{
                                "attribute-getter" : {
                                    "attribute" : "lcp_auth_protocol"
                                }
                            }';
                        }
                        leaf mru-negotiation {
                            type rtb-types:boolean-type;
                            description "MRU negotiation";
                            reference
                            '{
                                "attribute-getter" : {
                                    "attribute" : "lcp_mru_negotiation"
                                }
                            }';
                        }
                        leaf mru {
                            type uint16 { 
                                range "1280..1500";
                            }
                            description "Maximum local MRU";
                            reference
                            '{
                                "attribute-getter" : {
                                    "attribute" : "lcp_mru"
                                }
                            }';
                        } 
                        leaf mtu {
                            type uint16 { 
                                range "1280..1500";
                            }
                            description "Maximum local MTU";
                            reference
                            '{
                                "attribute-getter" : {
                                    "attribute" : "lcp_mtu"
                                }
                            }';
                        } 
                        leaf lcp-loop-detection {
                            type rtb-types:boolean-type;
                            description "Loop detection";
                            reference
                            '{
                                "attribute-getter" : {
                                    "attribute" : "lcp_loop_detection"
                                }
                            }';
                        } 
                        leaf echo-interval {
                            type uint8 { 
                                range "1..255";
                            }
                            description "Echo interval in seconds";
                            reference
                            '{
                                "attribute-getter" : {
                                    "attribute" : "lcp_echo_interval"
                                }
                            }';
                        } 
                        leaf echo-max-retransmit {
                            type uint8 { 
                                range "1..255";
                            }
                            description "Echo maximum retries";
                            reference
                            '{
                                "attribute-getter" : {
                                    "attribute" : "lcp_echo_max_retransmit"
                                }
                            }';
                        } 
                        leaf echo-enable {
                            type rtb-types:boolean-type;
                            description "Enable echo requests";
                            reference
                            '{
                                "attribute-getter" : {
                                    "attribute" : "lcp_echo_enabled"
                                }
                            }';
                        } 
                        leaf retransmit-interval {
                            type uint8 { 
                                range "1..255";
                            }
                            description "Retransmit interval in seconds";
                            reference
                            '{
                                "attribute-getter" : {
                                    "attribute" : "lcp_retransmit_interval"
                                }
                            }';
                        } 
                        leaf retransmit-max {
                            type uint8 { 
                                range "1..255";
                            }
                            description "Maximum retries";
                            reference
                            '{
                                "attribute-getter" : {
                                    "attribute" : "lcp_retransmit_max"
                                }
                            }';
                        } 
                        leaf config-nak-max {
                            type uint8 { 
                                range "1..255";
                            }
                            description "Max configure-reject/nak";
                            reference
                            '{
                                "attribute-getter" : {
                                    "attribute" : "lcp_config_nak_max"
                                }
                            }';
                        }
                    }
                    container ipcp {
                        description "Protocol IPCP";
                        reference
                        '{
                            "table-getter": {
                                "table-name" : "global.access.profile.config",
                                "type"    : "access_profile_config_table",
                                "inherit-attribute": ["access_profile_name"]
                            }
                        }';
                        leaf enable {
                            type rtb-types:boolean-type;
                            description "Enable PPP IPCP";
                            reference
                            '{
                                "attribute-getter" : {
                                    "attribute" : "ipcp_enabled"
                                }
                            }';
                        }
                        leaf passive {
                            type rtb-types:boolean-type;
                            description "Passive mode";
                            reference
                            '{
                                "attribute-getter" : {
                                    "attribute" : "ipcp_passive"
                                }
                            }';
                        } 
                        leaf retransmit-interval {
                            type uint8 { 
                                range "1..255";
                            }
                            description "Retransmit interval in seconds";
                            reference
                            '{
                                "attribute-getter" : {
                                    "attribute" : "ipcp_retransmit_interval"
                                }
                            }';
                        } 
                        leaf retransmit-max {
                            type uint8 { 
                                range "1..255";
                            }
                            description "Maximum retries";
                            reference
                            '{
                                "attribute-getter" : {
                                    "attribute" : "ipcp_retransmit_max"
                                }
                            }';
                        } 
                        leaf config-nak-max {
                            type uint8 { 
                                range "1..255";
                            }
                            description "Max configure-reject/nak";
                            reference
                            '{
                                "attribute-getter" : {
                                    "attribute" : "ipcp_config_nak_max"
                                }
                            }';
                        } 
                        leaf source-ifl {
                            type rtb-types:logical-interface-type;
                            description "Source IFL";
                            reference
                            '{
                                "attribute-getter" : {
                                    "attribute" : "ipcp_source_ifl",
                                    "expansion-getter" : {
                                        "package":"subsMgmt",
                                        "method" :"access_ifl_name_expander"
                                    }
                                }
                            }';
                        }
                    }
                    container ip6cp {
                        description "Protocol IP6CP";
                        reference
                        '{
                            "table-getter": {
                                "table-name" : "global.access.profile.config",
                                "type"    : "access_profile_config_table",
                                "inherit-attribute": ["access_profile_name"]
                            }
                        }';
                        leaf enable {
                            type rtb-types:boolean-type;
                            description "Enable PPP IP6CP";
                            reference
                            '{
                                "attribute-getter" : {
                                    "attribute" : "ip6cp_enabled"
                                }
                            }';
                        }
                        leaf passive {
                            type rtb-types:boolean-type;
                            description "Passive mode";
                            reference
                            '{
                                "attribute-getter" : {
                                    "attribute" : "ip6cp_passive"
                                }
                            }';
                        } 
                        leaf retransmit-interval {
                            type uint8 { 
                                range "1..255";
                            }
                            description "Retransmit interval in seconds";
                            reference
                            '{
                                "attribute-getter" : {
                                    "attribute" : "ip6cp_retransmit_interval"
                                }
                            }';
                        } 
                        leaf retransmit-max {
                            type uint8 { 
                                range "1..255";
                            }
                            description "Maximum retries";
                            reference
                            '{
                                "attribute-getter" : {
                                    "attribute" : "ip6cp_retransmit_max"
                                }
                            }';
                        } 
                        leaf config-nak-max {
                            type uint8 { 
                                range "1..255";
                            }
                            description "Max configure-reject/nak";
                            reference
                            '{
                                "attribute-getter" : {
                                    "attribute" : "ip6cp_config_nak_max"
                                }
                            }';
                        } 
                    }
                }
                container ra {
                    description "Protocol IPv6 router-advertisement";
                    reference
                    '{
                        "table-getter": {
                            "table-name" : "global.access.profile.config",
                            "type"    : "access_profile_config_table",
                            "inherit-attribute": ["access_profile_name"]
                        }
                    }';
                    leaf enable {
                        type rtb-types:boolean-type;
                        description "Enable IPv6 router-advertisement";
                        reference
                        '{
                            "attribute-getter" : {
                                "attribute" : "ipv6_ra_enabled"
                            }
                        }';
                    } 
                    leaf interval {
                        type uint8 { 
                            range "1..255";
                        }
                        description "Interval in seconds";
                        reference
                        '{
                            "attribute-getter" : {
                                "attribute" : "ipv6_ra_interval"
                            }
                        }';
                    } 
                    leaf lifetime {
                        type uint32 { 
                            range "0..4294967295";
                        }
                        description "Lifetime in seconds";
                        reference
                        '{
                            "attribute-getter" : {
                                "attribute" : "ipv6_ra_lifetime"
                            }
                        }';
                    } 
                    leaf preferred-lifetime {
                        type uint32 { 
                            range "0..4294967295";
                        }
                        description "Preferred lifetime in seconds";
                        reference
                        '{
                            "attribute-getter" : {
                                "attribute" : "ipv6_ra_preferred_lifetime"
                            }
                        }';
                    }
                }
                container dhcp {
                    description "Protocol DHCP";
                    reference
                    '{
                        "table-getter": {
                            "table-name" : "global.access.profile.config",
                            "type"    : "access_profile_config_table",
                            "inherit-attribute": ["access_profile_name"]
                        }
                    }';
                    leaf enable {
                        type rtb-types:boolean-type;
                        description "Enable DHCP";
                        reference
                        '{
                            "attribute-getter" : {
                                "attribute" : "ipv4_dhcp_enabled"
                            }
                        }';
                    } 
                    leaf mode {
                        type dhcp-mode;
                        description "DHCP mode";
                        reference
                        '{
                            "attribute-getter" : {
                                "attribute" : "ipv4_dhcp_mode"
                            }
                        }';
                    }
                    leaf lease-time {
                        type uint32 { 
                            range "1..4294967295";
                        }
                        description "DHCP lease time in seconds";
                        reference
                        '{
                            "attribute-getter" : {
                                "attribute" : "ipv4_dhcp_lease_time"
                            }
                        }';
                    }
                    leaf-list dhcp-server {
                        type string {
                            length "1 .. 64";
                        }
                        description "DHCP server";
                        reference
                        '{
                            "attribute-getter" : {
                                "attribute" : "dhcp_server_list",
                                "expansion-getter" : {
                                    "package":"subsMgmt",
                                    "method" :"access_dhcp_server_name_expander"
                                }
                            }
                        }';
                    }
                }
                container dhcpv6 {
                    description "Protocol DHCPv6";
                    reference
                    '{
                        "table-getter": {
                            "table-name" : "global.access.profile.config",
                            "type"    : "access_profile_config_table",
                            "inherit-attribute": ["access_profile_name"]
                        }
                    }';
                    leaf enable {
                        type rtb-types:boolean-type;
                        description "Enable DHCPv6";
                        reference
                        '{
                            "attribute-getter" : {
                                "attribute" : "ipv6_dhcpv6_enabled"
                            }
                        }';
                    }
                    leaf mode {
                        type dhcp-mode;
                        description "DHCPv6 mode";
                        reference
                        '{
                            "attribute-getter" : {
                                "attribute" : "ipv6_dhcpv6_mode"
                            }
                        }';
                    }
                    leaf lifetime {
                        type uint32 {
                            range "30..4294967295";
                        }
                        description "Lifetime in seconds";
                        reference
                        '{
                            "attribute-getter" : {
                                "attribute" : "ipv6_dhcpv6_lifetime"
                            }
                        }';
                    } 
                    leaf preferred-lifetime {
                        type uint32 {
                            range "30..4294967295";
                        }
                        description "Preferred lifetime in seconds";
                        reference
                        '{
                            "attribute-getter" : {
                                "attribute" : "ipv6_dhcpv6_preferred_lifetime"
                            }
                        }';
                    }
                    leaf-list dhcpv6-server {
                        type string {
                            length "1 .. 64";
                        }
                        description "DHCPv6 server";
                        reference
                        '{
                            "attribute-getter" : {
                                "attribute" : "dhcpv6_server_list",
                                "expansion-getter" : {
                                    "package":"subsMgmt",
                                    "method" :"access_dhcpv6_server_name_expander"
                                }
                            }
                        }';
                    }
                }
                container l2tp {
                    description "Protocol L2TP";
                    reference
                    '{
                        "table-getter": {
                            "table-name" : "global.access.profile.config",
                            "type" : "access_profile_config_table",
                            "inherit-attribute": ["access_profile_name"]
                        }
                    }';
                    leaf tunnel-profile {
                        type string {
                            length "1..64";
                        }
                        description "L2TP tunnel profile";
                        reference
                        '{
                            "attribute-getter" : {
                                "attribute" : "l2tp_tunnel_profile_name"
                            }
                        }';
                    }
                }
                container ipoe {
                    description "Protocol IPoE";
                    reference
                    '{
                        "table-getter": {
                            "table-name" : "global.access.profile.config",
                            "type" : "access_profile_config_table",
                            "inherit-attribute": ["access_profile_name"]
                        }
                    }';
                    leaf ip-mtu-profile {
                        type leafref {
                            path "../../../../../forwarding-options/mtu-profile/mtu-profile-name";
                        }

                        must '(../../../../../forwarding-options/mtu-profile[mtu-profile-name=current()]/type = "ip")' {
                            error-message "IPoE MTU profile not of type IP";
                        }

                        description "Configure subscriber IP MTU profile";
                        reference
                        '{
                            "attribute-getter" : {
                                "attribute" : "ipoe_mtu_profile_name",
                                "expansion-getter" : {
                                    "package":"subsMgmt",
                                    "method" :"access_ip_mtu_profile_expander"
                                }
                            }
                        }';
                    } 
                }
            }
            container address-family {
                description "Address-family configuration";
                container ipv4 {
                    description "Configure address family IPv4 specific parameters";
                    reference
                    '{
                        "table-getter": {
                            "table-name" : "global.access.profile.config",
                            "type"    : "access_profile_config_table",
                            "inherit-attribute": ["access_profile_name"]
                        }
                    }';
                    leaf enable {
                        type rtb-types:boolean-type;
                        description "Enable IPv4";
                        reference
                        '{
                            "attribute-getter" : {
                                "attribute" : "ipv4_enabled"
                            }
                        }';
                    } 
                    leaf pool-name {
                        type string {
                            length "1..64";
                        }
                        description "Local IPv4 pool name";
                        reference
                        '{
                            "attribute-getter" : {
                                "attribute" : "ipv4_address_pool_name"
                            }
                        }';
                    } 
                    leaf static-ipv4 {
                        type inet:ipv4-address;
                        description "Static address";
                        reference
                        '{
                            "attribute-getter" : {
                                "attribute" : "static_ipv4_address"
                            }
                        }';
                    } 
                    leaf primary-dns {
                        type inet:ipv4-address;
                        description "Primary DNS server";
                        reference
                        '{
                            "attribute-getter" : {
                                "attribute" : "ipv4_dns_primary_address"
                            }
                        }';
                    } 
                    leaf secondary-dns {
                        type inet:ipv4-address;
                        description "Secondary DNS server";
                        reference
                        '{
                            "attribute-getter" : {
                                "attribute" : "ipv4_dns_secondary_address"
                            }
                        }';
                    }
                    leaf dad-enable {
                        type rtb-types:boolean-type;
                        description "Enable/disable IPv4 duplicate address detection (enabled by default)";
                        reference
                        '{
                            "attribute-getter" : {
                                "attribute" : "ipv4_dad_enabled"
                            }
                        }';
                    }
                    leaf proxy-arp-enable {
                        type rtb-types:boolean-type;
                        autocli:hide;
                        description "Enable Proxy ARP";
                        reference
                        '{
                            "attribute-getter" : {
                                "attribute" : "proxy_arp_enabled"
                            }
                        }';
                    }
                    leaf proxy-arp {
                        type proxy-arp-mode;
                        description "Enable Proxy ARP mode";
                        reference
                        '{
                            "attribute-getter" : {
                                "attribute" : "proxy_arp_mode"
                            }
                        }';
                    }
                }
                container ipv6 {
                    description "Configure address family IPv6 specific parameters";
                    reference
                    '{
                        "table-getter": {
                            "table-name" : "global.access.profile.config",
                            "type"    : "access_profile_config_table",
                            "inherit-attribute": ["access_profile_name"]
                        }
                    }';
                    leaf enable {
                        type rtb-types:boolean-type;
                        description "Enable IPv6";
                        reference
                        '{
                            "attribute-getter" : {
                                "attribute" : "ipv6_enabled"
                            }
                        }';
                    } 
                    leaf pool-name {
                        type string {
                            length "1..64";
                        }
                        description "Local IPv6 pool name";
                        reference
                        '{
                            "attribute-getter" : {
                                "attribute" : "ipv6_prefix_pool_name"
                            }
                        }';
                    } 
                    leaf prefix-delegation-pool-name {
                        type string {
                            length "1..64";
                        }
                        description "Local IPv6 prefix delegation pool name";
                        reference
                        '{
                            "attribute-getter" : {
                                "attribute" : "ipv6_prefix_delegation_pool_name"
                            }
                        }';
                    } 
                    leaf primary-dns {
                        type inet:ipv6-address;
                        description "Primary DNS server";
                        reference
                        '{
                            "attribute-getter" : {
                                "attribute" : "ipv6_dns_primary_address"
                            }
                        }';
                    } 
                    leaf secondary-dns {
                        type inet:ipv6-address;
                        description "Secondary DNS server";
                        reference
                        '{
                            "attribute-getter" : {
                                "attribute" : "ipv6_dns_secondary_address"
                            }
                        }';
                    }
                    leaf dad-enable {
                        type rtb-types:boolean-type;
                        description "Enable/disable IPv6 duplicate address detection (enabled by default)";
                        reference
                        '{
                            "attribute-getter" : {
                                "attribute" : "ipv6_dad_enabled"
                            }
                        }';
                    }
                }
            }
        }
    }
}
