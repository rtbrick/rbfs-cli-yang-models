submodule rtbrick-access-service-profile {

    yang-version 1.1;

    belongs-to rtbrick-config {
        prefix config;
    }

    import rtbrick-types {
        prefix "rtb-types";
    }
    include rtbrick-forwarding-options;
    include rtbrick-multicast-options;
    organization
      "RtBrick";
    contact
      "yang-support@rtbrick.com";
    description
      "This sub-module defines the YANG structure for the access service profile.";
    revision 2020-07-24 {
        description "First revision";
        reference "None";
    }

    typedef version {
        type enumeration {
            enum IGMPv1 {
                value "0";
            }
            enum IGMPv2 {
                value "1";
            }
            enum IGMPv3 {
                value "2";
            }
        }
        description "IGMP version";
    }

    grouping access-service-profile {
        description "Global access service profile configuration";

        list service-profile {
            key "profile-name";
            description "Global service profile configuration";
            reference
            '{
                "table-getter": {
                    "table-name": "global.access.service.profile.config",
                    "type": "service_profile_config_table"
                }
            }';
            leaf profile-name {
                type string {
                    length "1..64";
                }
                description "Name of the service profile";
                reference
                '{
                    "attribute-getter": {
                        "attribute": "service_profile_name"
                    }
                }';
            }
            container address-translation {
                description "Configure NAT for subscriber";
                reference
                '{
                    "table-getter": {
                        "table-name": "global.access.service.profile.config",
                        "type": "service_profile_config_table",
                        "inherit-attribute" : [ "service_profile_name" ]
                    }
                }';
                leaf profile {
                    type string {
                        length "1..64";
                    }
                    description "NAT profile";
                    reference
                    '{
                        "attribute-getter": {
                            "attribute": "nat_profile_name",
                            "expansion-getter": {
                                "package": "subsMgmt",
                                "method": "access_nat_profile_name_expander"
                            }
                        }
                    }';
                }
            }
            container qos {
                description "QoS related attributes";
                reference
                '{
                    "table-getter": {
                        "table-name": "global.access.service.profile.config",
                        "type": "service_profile_config_table",
                        "inherit-attribute": ["service_profile_name"]
                    }
                }';
                leaf profile {
                    type string {
                        length "1..64";
                    }
                    description "QoS profile";
                    must '/forwarding-options/class-of-service/profile[profile-name = current()]' {
                        error-message "QoS profile referenced in service-profile does not exist";
                    }
                    reference
                    '{
                        "attribute-getter": {
                            "attribute": "qos_profile_name",
                            "expansion-getter": {
                                "package": "subsMgmt",
                                "method": "access_qos_profile_name_expander"
                            }
                        }
                    }';
                }
                leaf parent-scheduler {
                    type string {
                        length "1..64";
                    }
                    description "QoS parent scheduler";
                    must '/forwarding-options/class-of-service/scheduler[scheduler-name = current()]' {
                        error-message "QoS parent scheduler referenced in service-profile does not exist";
                    }
                    reference
                    '{
                        "attribute-getter": {
                            "attribute": "qos_parent_scheduler_name"
                        }
                    }';
                }
                leaf multifield-classifier-name {
                    type string {
                        length "1..64";
                    }
                    description "QoS Ingress MFC";
                    must '/forwarding-options/class-of-service/multifield-classifier/acl/l3v4/rule[rule-name = current()] or /forwarding-options/class-of-service/multifield-classifier/acl/l3v6/rule[rule-name = current()]' {
                        error-message "QoS multifield classifier referenced in service-profile does not exist";
                    }
                    reference
                    '{
                        "attribute-getter": {
                            "attribute": "mf_classifier_name"
                        }
                    }';
                }
            }
            container igmp {
                description "IGMP related attributes";
                reference
                '{
                    "table-getter": {
                        "table-name": "global.access.service.profile.config",
                        "type": "service_profile_config_table",
                        "inherit-attribute": ["service_profile_name"]
                    }
                }';
                leaf enable {
                    type rtb-types:boolean-type;
                    description "Enable IGMP service";
                    reference
                    '{
                        "attribute-getter": {
                            "attribute": "igmp_enabled"
                        }
                    }';
                }
                leaf profile {
                    type string {
                        length "1..64";
                    }
                    description "IGMP profile";
                    must '/multicast-options/igmp/interface-profile[profile-name = current()]' {
                        error-message "IGMP profile referenced in service-profile does not exist";
                    }
                    reference
                    '{
                        "attribute-getter": {
                            "attribute": "igmp_profile"
                        }
                    }';
                }
                leaf version {
                    type version;
                    description "IGMP version";
                    reference
                    '{
                        "attribute-getter": {
                            "attribute": "igmp_version"
                        }
                    }';
                }
                leaf max-members {
                    type uint32;
                    description "Maximum IGMP membership per subscriber";
                    reference
                    '{
                        "attribute-getter": {
                            "attribute": "igmp_max_members"
                        }
                    }';
                }
            }
            container http-redirect {
                description "HTTP redirect related attributes";
                reference
                '{
                    "table-getter": {
                        "table-name": "global.access.service.profile.config",
                        "type": "service_profile_config_table",
                        "inherit-attribute": ["service_profile_name"]
                    }
                }';
                leaf url {
                    type string {
                        length "1..256";
                    }
                    description "HTTP redirect url";
                    reference
                    '{
                        "attribute-getter": {
                            "attribute": "http_redirect_url"
                        }
                    }';
                }
            }
            container acl {
                description "Subscriber ACL related attributes";
                reference
                '{
                    "table-getter": {
                        "table-name": "global.access.service.profile.config",
                        "type": "service_profile_config_table",
                        "inherit-attribute": ["service_profile_name"]
                    }
                }';
                leaf ipv4-acl-in {
                    type string {
                        length "1..64";
                    }
                    description "Ingress IPv4 subscriber ACL name";
                    must '/forwarding-options/subscriber-acl/l3v4/rule[rule-name = current()]' {
                        error-message "Ingress IPv4 subscriber ACL referenced in service-profile does not exist";
                    }
                    reference
                    '{
                        "attribute-getter": {
                            "attribute": "ipv4_acl_in"
                        }
                    }';
                }
                leaf ipv4-acl-out {
                    type string {
                        length "1..64";
                    }
                    description "Egress IPv4 subscriber ACL name";
                    must '/forwarding-options/subscriber-acl/l3v4/rule[rule-name = current()]' {
                        error-message "Egress IPv4 subscriber ACL referenced in service-profile does not exist";
                    }
                    reference
                    '{
                        "attribute-getter": {
                            "attribute": "ipv4_acl_out"
                        }
                    }';
                }
                leaf ipv6-acl-in {
                    type string {
                        length "1..64";
                    }
                    description "Ingress IPv6 subscriber ACL name";
                    must '/forwarding-options/subscriber-acl/l3v6/rule[rule-name = current()]' {
                        error-message "Ingress IPv6 subscriber ACL referenced in service-profile does not exist";
                    }
                    reference
                    '{
                        "attribute-getter": {
                            "attribute": "ipv6_acl_in"
                        }
                    }';
                }
                leaf ipv6-acl-out {
                    type string {
                        length "1..64";
                    }
                    description "Egress IPv6 subscriber ACL name";
                    must '/forwarding-options/subscriber-acl/l3v6/rule[rule-name = current()]' {
                        error-message "Egress IPv6 subscriber ACL referenced in service-profile does not exist";
                    }
                    reference
                    '{
                        "attribute-getter": {
                            "attribute": "ipv6_acl_out"
                        }
                    }';
                }
            }
        }
    }
}
