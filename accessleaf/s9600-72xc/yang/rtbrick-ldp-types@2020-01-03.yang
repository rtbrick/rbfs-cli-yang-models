module rtbrick-ldp-types {
    yang-version 1.1;
    namespace
    "urn:config:rtbrick:ldp:types";
    prefix rtb-ldp-types;

    organization 
        "RtBrick";

    contact
      "yang-support@rtbrick.com";

    description
      "This module contains dummy data definitions for use in LDP YANG
    model.";

    revision "2020-01-03" {
      description "Dummy LDP types for rtbrick";
      reference "None";
    }
}
