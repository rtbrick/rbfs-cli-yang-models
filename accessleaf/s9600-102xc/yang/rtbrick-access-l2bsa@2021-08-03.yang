submodule rtbrick-access-l2bsa {

    yang-version 1.1;                                                                

    belongs-to rtbrick-config {
        prefix config;
    }

    import rtbrick-types {
        prefix "rtb-types";
    }

    import clixon-autocli{
        prefix autocli;
    }

    organization
      "RtBrick";
    contact
      "Authors: Vyshakh Krishnan (vyshakh@rtbrick.com)";
    description
      "This sub-module contains yang structure for
       access l2bsa configurations.";
    revision 2021-08-03 {
        description "First revision";
        reference "None";
    }

    typedef l2bsa-ia-vlan-mode {
        type enumeration {
            enum SINGLE {
                value "1";
            }
            enum DOUBLE {
                value "2";
            }
            enum SINGLE_DOUBLE {
                value "3";
            }
        }
        description "L2BSA intermediate agent VLAN modes";
    }

    grouping access-l2bsa {
        description "Global access l2bsa configurations";
        container l2bsa {
            description "Global access l2bsa configurations";
            container intermediate-agent {
                description "Global l2bsa intermediate agent configurations";
                list interface {
                    key "interface-name";
                    description "L2bsa intermediate agent interface configurations";
                    reference
                    '{
                        "table-getter": {
                            "table-name" : "global.access.l2bsa.ia.interface.config",
                            "type"    : "l2bsa_ia_config_table"
                        }
                    }';
                    leaf interface-name {
                        type rtb-types:interface-type;
                        description "Name of the physical interface";
                        reference
                        '{
                            "attribute-getter" : {
                                "attribute" : "interface_name",
                                "expansion-getter" : {
                                    "package":"subsMgmt",
                                    "method" :"access_ifp_name_expander"
                                }
                            }
                        }';
                    }
                    leaf inner-vlan-min {
                        type uint16 { 
                            range "1..4094";
                        }
                        description "Inner VLAN min <1-4094>";
                        reference
                        '{
                            "attribute-getter" : {
                                "attribute" : "inner_vlan_min"
                            }
                        }';
                    }
                    leaf inner-vlan-max {
                        type uint16 { 
                            range "1..4094";
                        }
                        description "Inner VLAN max <1-4094>";
                        reference
                        '{
                            "attribute-getter" : {
                                "attribute" : "inner_vlan_max"
                            }
                        }';
                    }
                    leaf vlan-mode {
                        type l2bsa-ia-vlan-mode; 
                        description "L2BSA intermediate agent VLAN mode";
                        reference
                        '{
                            "attribute-getter" : {
                                "attribute" : "vlan_mode"
                            }
                        }';
                    }
                    leaf pppoe-enable {
                        type rtb-types:boolean-type;
                        description "Enable/disable the L2BSA intermediate agent for PPPoE Discovery";
                        reference
                        '{
                            "attribute-getter" : {
                                "attribute" : "pppoe_enabled"
                            }
                        }';
                    }
                    leaf dhcpv4-enable {
                        type rtb-types:boolean-type;
                        description "Enable/disable the L2BSA intermediate agent for DHCPv4";
                        reference
                        '{
                            "attribute-getter" : {
                                "attribute" : "dhcpv4_enabled"
                            }
                        }';
                    }
                    leaf dhcpv6-enable {
                        type rtb-types:boolean-type;
                        autocli:hide;
                        description "Enable/disable the L2BSA intermediate agent for DHCPv6";
                        reference
                        '{
                            "attribute-getter" : {
                                "attribute" : "dhcpv6_enabled"
                            }
                        }';
                    }
                }
            }
        }  
    }
}
