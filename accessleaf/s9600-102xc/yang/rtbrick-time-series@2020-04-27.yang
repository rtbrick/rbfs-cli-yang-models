submodule rtbrick-time-series {
    yang-version 1.1;
    belongs-to rtbrick-config {
        prefix config;
    }

    import rtbrick-types {
        prefix "rtb-types";
    }

    organization
      "Rtbrick";
    contact
      "yang-support@rtbrick.com";
    description
      "This sub-module contains the YANG structure for the time series configuration, that can interact with Prometheus.
       time-series
           +-> { metrics }
               +-> { metric config}
           +-> {alert}
             +-> { alert config }
      ";
    revision 2020-04-27 {
        description "First revision";
        reference "None";
    }
    /* Typedefs */
    typedef bds-match-type {
        type enumeration {
            enum exact {
                value "0";
                description "Exact Match";
            }
            enum regular-expression {
                value "1";
                description "Regular expression match";
            }
        }
        description "Metric match BDS type";
    }

    typedef prometheus-metric-type {
        type enumeration {
            enum counter {
                value "0";
                description "Counter";
            }
            enum gauge {
                value "1";
                description "Gauge";
            }
        }
        description "Prometheus metric types";
    }

    typedef label-type {
        type enumeration {
            enum static {
                value "0";
                description "Static";
            }
            enum dynamic {
                value "1";
                description "Dynamic";
            }
        }
        description "Prometheus label types";
    }

    typedef bds-metric-type {
        type enumeration {
            enum index-metric {
                value "0";
                description "Metric from BDS Table Metadata";
            }
            enum object-metric {
                value "1";
                description "Metric from BDS object attributes";
            }
        }
        description "Metric type from a BDS perspective";
    }
    typedef keyval-string {
        type string {
             pattern '.*:.*';
             length "1..128";
        }
        description "A BDS key-value string";
    }

    typedef prometheus-label-key {
        type string {
            pattern '[a-zA-Z_][a-zA-Z0-9_]*';
            length "1..128";
        }
        description "Prometheus Label key format";
    }

    typedef prometheus-metric-name {
        type string {
            pattern '[a-zA-Z_:][a-zA-Z0-9_:]*';
            pattern '([^r].*|r([^t].*|$)|rt([^b].*|$)|rtb([^r].*|$)|rtbr([^i].*|$)|rtbri([^c].*|$)|rtbric([^k].*|$)|.{0,6})' {
                error-message "Metric name must not start with 'rtbrick'.";
            }
            length "1..128";
        }
        description "Prometheus Metric name format";
    }

    typedef match-negate-type {
        type enumeration {
            enum false {
                value "0";
                description "Don't return negate";
            }
            enum true {
                value "1";
                description "Return negate";
            }
        }
    }

    typedef prometheus-scrape-interval {
        type string {
            pattern '\d+[ms]';
            length "1..128";
        }
        description "Prometheus scrape interval format";
    }
    typedef prometheus-repeat-interval {
        type string {
            pattern '\d+[msh]';
            length "1..128";
        }
        description "Prometheus repeat interval format";
    }

    /* Time series hierarchy */
    container time-series {
        description "Time series Hierarchy";
        must 'count(metric-profile) <= 100' {
            error-message "Maximum number of metric-profiles allowed is 100";
        }
        reference
        '{
            "table-getter": {
                "table-name": "global.time-series.config",
                "type"   : "time_series_global_config_table",
                "default-attribute" : [ {"configuration_name" : "rtbrick" }, {"time-series-history-enable" : "disable"} ]
            }
        }';
        leaf history-status {
            type rtb-types:enable-disable-type;
            description "TSDB query history status";
            reference
            '{
                "attribute-getter" : {
                    "attribute": "time-series-history-enable"
                }
            }';
        }
        list metric-profile {
            key "profile-name";
            description "Metric profile configuration";
            reference
            '{
                "table-getter": {
                    "table-name": "global.time-series.profile.config",
                    "type": "time_series_profile_config_table",
                    "default-attribute": [{"scrape-interval": "5s"}, {"append-timestamp": "false"}]
                }
            }';
            leaf profile-name {
                type string{
                    pattern '([^r].*|r([^t].*|$)|rt([^b].*|$)|rtb([^r].*|$)|rtbr([^i].*|$)|rtbri([^c].*|$)|rtbric([^k].*|$)|.{0,6})' {
                        error-message "Profile name must not start with 'rtbrick'.";
                    }
                    length "1..128";
                }
                mandatory true;
                description "Metrics profile name";
                reference
                '{
                    "attribute-getter": {
                        "attribute": "profile-name"
                    }
                }';
                must '. != "default"' {
                    error-message "Profile name cannot be default";
                }
            }
            leaf scrape-interval {
                type prometheus-scrape-interval;
                description "Scrape interval with amount and unit. The amount is an integer value. The unit is m for minutes and s for seconds";
                reference
                '{
                    "attribute-getter": {
                        "attribute": "scrape-interval"
                    }
                }';
            }
            leaf append-timestamp {
                type rtb-types:boolean-type;
                description "Specifies if the sample timestamp should be appended.";
                reference
                '{
                    "attribute-getter": {
                        "attribute": "append-timestamp"
                    }
                }';
            }
        }
        list metric {
            key "name";
            description "Metric configuration";
            reference
            '{
                "table-getter": {
                    "table-name": "global.time-series.metric.config",
                    "type"   : "time_series_metric_config_table",
                    "default-attribute": [{"profile-name": "default"}]
                }
            }';
            must 'count(attribute) >= 1' {
                error-message "Attribute configuration is mandatory";
            }
            leaf name {
                type prometheus-metric-name;
                mandatory true;
                description "Metric name";
                reference
                '{
                    "attribute-getter" : {
                        "attribute" : "metric-name"
                    }
                }';
            }
            leaf table-name {
                type string{
                    length "1..128";
                }
                mandatory true;
                description "Table Name";
                reference
                '{
                    "attribute-getter" : {
                        "attribute" : "table-name"
                    }
                }';
            }
            leaf profile-name {
                must "(../../metric-profile[profile-name=current()])" {
                    error-message "Profile must be configured first";
                }
                type string{
                    length "1..128";
                }
                description "Profile name";
                reference
                '{
                    "attribute-getter" : {
                        "attribute" : "profile-name",
                        "expansion-getter" : {
                            "package":"bds",
                            "method" :"bds_profile_name_expander"
                        }
                    }
                }';
            }
            leaf include-subscribed-tables {
                type rtb-types:boolean-type;
                description "Whether we should apply this configuration on a subscribed tables as well, [false by default]";
                reference
                '{
                    "attribute-getter" : {
                        "attribute" : "include-subscribed-tables"
                    }
                }';
            }
            leaf append-timestamp {
                type rtb-types:boolean-type;
                description "Whether we should append timestamp for every metric, [false by default]";
                reference
                '{
                    "attribute-getter" : {
                        "attribute" : "append-timestamp"
                    }
                }';
            }
            leaf bds-type {
                type bds-metric-type;
                mandatory true;
                description "Metric BDS type";
                reference
                '{
                    "attribute-getter" : {
                        "attribute" : "metric-bds-type"
                    }
                }';
            }
            leaf prometheus-type {
                type prometheus-metric-type;
                mandatory true;
                description "Metric Prometheus type";
                reference
                '{
                    "attribute-getter" : {
                        "attribute" : "metric-prometheus-type"
                    }
                }';
            }
            leaf index-name {
                when "../bds-type='index-metric'";
                type string {
                    length "1..64";
                }
                description "Table Index name, for index-metrics";
                reference
                '{
                    "attribute-getter" : {
                        "attribute" : "index-name"
                    }
                }';
            }
            leaf description {
                type string {
                    length "1..256";
                }
                mandatory true;
                description "Description for this metric";
                reference
                '{
                    "attribute-getter" : {
                        "attribute" : "metric-description"
                    }
                }';
            }

            list filter {
                must '../bds-type !="index-metric"' {
                    error-message "Invalid config: filter is not valid for index metric";
                }
                key "match-attribute-name";
                description "Metric filter configuration";
                reference
                '{
                    "table-getter": {
                        "table-name": "global.time-series.filter.metric.config",
                        "type" :  "time_series_filter_metric_config_table",
                        "inherit-attribute": [ "metric-name" ],
                        "default-attribute": [{"match-negate" : "false"}]
                    }
                }';

                leaf match-attribute-name {
                    type string {
                        length "1..128";
                    }
                    mandatory true;
                    description "Matching attribute name for this filter";
                    reference
                    '{
                        "attribute-getter" : {
                            "attribute" : "match-attribute-name"
                        }
                    }';
                }
                leaf match-attribute-value {
                    type string {
                        length "1..128";
                    }
                    mandatory true;
                    description "Matching attribute value for this filter (regex pattern should be as per POSIX standard)";
                    reference
                        '{
                            "attribute-getter" : {
                                "attribute" : "match-attribute-value"
                            }
                        }';
                }
                leaf match-type {
                    type bds-match-type;
                    mandatory true;
                    description "Match type [regular-expression or exact]";
                    reference
                        '{
                            "attribute-getter" : {
                                "attribute" : "match-type"
                            }
                        }';
                }
                leaf match-negate {
                    type match-negate-type;
                    description "Match-negate [True or False]";
                    reference
                        '{
                            "attribute-getter" : {
                                "attribute" : "match-negate"
                            }
                        }';
                }
            }

            list attribute {
                key "attribute-name";
                description "Metric attribute configuration";
                reference
                    '{
                        "table-getter": {
                                "table-name": "global.time-series.attribute.config",
                                "type" :  "time_series_attribute_config_table",
                                "inherit-attribute": [ "metric-name" ]
                        }
                    }';

                leaf attribute-name {
                    type string {
                        length "1..128";
                    }
                    mandatory true;
                    description "Attribute that needs to be rendered as a metric";
                    reference
                    '{
                        "attribute-getter" : {
                            "attribute" : "attribute-name"
                        }
                    }';
                }
                list label{
                    key "label-key";
                    description "Label key configuration";
                    reference
                    '{
                        "table-getter": {
                            "table-name": "global.time-series.label.config",
                            "type" :  "time_series_label_config_table",
                            "inherit-attribute": [ "metric-name", "attribute-name" ]
                        }
                    }';

                    leaf label-key {
                        type prometheus-label-key;
                        mandatory true;
                        description "Key for the label";
                        must '. != "element_name" and . != "pod_name" and . != "bd_name"'{
                            error-message "User configured label key shouldn't be same as default label key";
                        }
                        reference
                        '{
                            "attribute-getter" : {
                                "attribute" : "label-key"
                            }
                        }';
                    }
                    leaf label-value {
                        type string {
                            length "1..128";
                        }
                        mandatory true;
                        description "Value of the label";
                        reference
                        '{
                            "attribute-getter" : {
                                "attribute" : "label-value"
                            }
                        }';
                    }
                    leaf label-type {
                        type label-type;
                        mandatory true;
                        description "Label type can be dynamic/static";
                        reference
                        '{
                            "attribute-getter" : {
                                "attribute" : "label-type"
                            }
                        }';
                    }
                }
            }
        }
        list alert-profile {
            key "profile-name";
            description "Metric alert-profile configuration";
            reference
            '{
                "table-getter": {
                    "table-name": "global.time-series.alert.profile.config",
                    "type": "time_series_alert_profile_config_table",
                    "default-attribute": [{"repeat-interval": "4h"}, {"group-by": "..."}],
                     "notification-type" : "table-change",                    
                     "notification-interval": 500
                }
            }';
            leaf profile-name {
                type string{
                    length "1..128";
                }
                mandatory true;
                description "Metrics alert-profile name";
                reference
                '{
                    "attribute-getter": {
                        "attribute": "profile-name"
                    }
                }';
            }
            leaf priority {
                mandatory true;
                type uint16;
                description "Profile priority";
                reference
                    '{
                        "attribute-getter" : {
                            "attribute" : "priority"
                        }
                    }';
            }
            leaf repeat-interval {
                type prometheus-repeat-interval;
                description "Repeat interval with amount and unit. [Default: 4h]";
                reference
                '{
                    "attribute-getter": {
                        "attribute": "repeat-interval"
                    }
                }';
            }
            leaf-list group-by {
                type string{
                    length "1..128";
                }
                description "The label names to group alerts to avoid duplicate alert notifications";
                reference
                '{
                    "attribute-getter" : {
                        "attribute" : "group-by"
                    }
                }';
            }
            leaf-list matchers {
                type string{
                    length "1..128";
                }
                description "abel constraints to match alert notifications";
                reference
                '{
                    "attribute-getter" : {
                        "attribute" : "matchers"
                    }
                }';
            }
        }
        list alert {
            key "name";
            description "Alert configuration";
            reference
            '{
                "table-getter": {
                    "table-name": "global.time-series.alert.config",
                    "type"   : "time_series_alert_config_table",
                    "notification-type" : "table-change",
                    "notification-interval": 500
                }
            }';
            leaf name {
                type string {
                    length "1..128";
                }
                mandatory true;
                description "Name of the alert";
                reference
                '{
                    "attribute-getter" : {
                        "attribute" : "alert-name"
                    }
                }';
            }
            leaf group {
                type string {
                    length "1..128";
                }
                mandatory true;
                description "Group of the alert";
                reference
                '{
                    "attribute-getter" : {
                        "attribute" : "alert-group-name"
                    }
                }';
            }
            leaf for{
                type  string {
                    length "1..64";
                    pattern '[0-9]+(ms|[smhdwy])';
                }
                description "Interval for the alert has to be active after which prometheus will fire the alert";
                reference
                '{
                    "attribute-getter" : {
                        "attribute" : "for"
                    }
                }';
            }

            leaf interval{
                type  string {
                    length "1..64";
                    pattern '[0-9]+(ms|[smhdwy])';
                }
                mandatory true;
                description "Evaluation interval of this alert";
                reference
                '{
                    "attribute-getter" : {
                        "attribute" : "interval"
                    }
                }';
            }
            leaf expr{
                type string {
                    length "1..512";
                }
                mandatory true;
                description "PromQL Alert evaluation expression for execution of this alert";
                reference
                '{
                    "attribute-getter" : {
                        "attribute" : "expr"
                    }
                }';
            }
            leaf level {
                type string {
                    pattern  '[0-7]';
                    length "1..128";
                }
                mandatory true;
                description "Explicit annotation label level [0 to 7]";
                reference
                '{
                    "attribute-getter" : {
                        "attribute" : "level"
                    }
                }';
            }
            leaf summary {
                type string {
                    length "1..128";
                }
                mandatory true;
                description "Explicit annotation label summary";
                reference
                '{
                    "attribute-getter" : {
                        "attribute" : "summary"
                    }
                }';
            }
            leaf description {
                type string {
                    length "1..256";
                }
                mandatory true;
                description "Alert description";
                reference
                '{
                    "attribute-getter" : {
                        "attribute" : "description"
                    }
                }';
            }
            leaf-list labels {
                type keyval-string;
                ordered-by user;
                description "Key,value pair of labels for this alert";
                reference
                '{
                    "attribute-getter" : {
                        "attribute" : "labels"
                    }
                }';
            }
            leaf-list annotations {
                type keyval-string;
                ordered-by user;
                description "Key,value pair of annotations for this alert";
                reference
                '{
                    "attribute-getter" : {
                        "attribute" : "annotations"
                    }
                }';
            }
        }
        container self-monitoring {
            description "Prometheus self-monitoring configuration";
            reference
            '{
                "table-getter": {
                    "table-name": "global.time-series.self-monitoring",
                    "type": "time_series_self_monitoring_table",
                    "default-attribute": [{"configuration_name": "rtbrick"}, {"scrape-interval": "5s"}, {"enable": "false"}],
                    "notification-type" : "table-change",                    
                    "notification-interval": 500
                }
            }';
            leaf enable {
                type rtb-types:boolean-type;
                description "Specifies if self monitoring should be enabled.";
                reference
                '{
                    "attribute-getter": {
                        "attribute": "enable"
                    }
                }';
            }
            leaf scrape-interval {
                type prometheus-scrape-interval;
                description "Scrape interval with amount and unit. The amount is an integer value. The unit is m for minutes and s for seconds";
                reference
                '{
                    "attribute-getter": {
                        "attribute": "scrape-interval"
                    }
                }';
            }
        }
    }
}
