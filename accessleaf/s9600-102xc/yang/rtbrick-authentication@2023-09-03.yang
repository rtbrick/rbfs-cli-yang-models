submodule rtbrick-authentication {
    yang-version 1.1;

    belongs-to rtbrick-config {
        prefix config;
    }

    import rtbrick-types {
       prefix rtb-types;
    }

    organization
      "Rtbrick";
    contact
      "Author : Ankit (ankit@rtbrick.com)";

    description
      "This is authentication related configuration YANG file";

    revision 2023-09-03 {
        description
        "First draft";

        reference "None";
    }

    typedef auth-type {
        type enumeration {
            enum clear-text {
                value "1";
                description "Plain text type";
            }
            enum md5 {
                value "2";
                description "Plain text type";
            }
            enum hmac-sha-1 {
                value "3";
                description "Plain text type";
            }
            enum hmac-sha-256 {
                value "4";
                description "Plain text type";
            }
            enum hmac-sha-384 {
                value "5";
                description "Plain text type";
            }
            enum hmac-sha-512 {
                value "6";
                description "Plain text type";
            }
        }
    }

    grouping authentication-key {
        description
        "Grouping containing a authentication keys config.";
        list key {
            key "key-id";
            description
                    "Authentication key-id";
            reference
            '{
                "table-getter": {
                    "table-name" : "global.auth.profile.config",
                    "type"    :  "auth_profile_table",
                    "inherit-attribute":[ "profile_name" ]
                }
            }';
            leaf key-id {
                type uint32 {
                    range "1 .. 255";
                }
                description
                    "Key-id value for authentication exchange";
                reference
                '{
                    "attribute-getter" : {
                        "attribute" : "key"
                    }
                 }';
            }
            leaf type {
                type auth-type;
                description
                    "Authentication type";
                reference
                '{
                    "attribute-getter" : {
                        "attribute" : "type"
                    }
                 }';
            }
            leaf plain-text {
                type string {
                    length "1..64";
                }
                description
                    "Authentication password";
                reference
                '{
                    "attribute-getter" : {
                        "attribute" : "password",
                        "plain-text-password" : true,
                        "secret-text-leaf-name" : "encrypted-text"
                    }
                 }';
            }
            leaf encrypted-text {
                type rtb-types:secret-string-type;
                description
                    "Authentication password encrypted";
                reference
                '{
                    "attribute-getter" : {
                        "attribute" : "password"
                    }
                 }';
            }
        }
    }

    grouping authentication-top {
        description
        "Top-level grouping containing a authentication config.";
        list authentication-profile {
            key "name";
            description
                    "Authentication profile name";
            reference
            '{
                "table-getter": {
                    "table-name" : "global.auth.config",
                    "type"    :  "auth_table"
                }
            }';
            leaf name {
                type rtb-types:string64;
                description
                    "An operator-assigned unique name for the authentication profile";
                reference
                '{
                    "attribute-getter" : {
                        "attribute" : "profile_name"
                    }
                 }';
            }
            leaf prefer-key-id {
                type uint32;
                description
                    "Preferred key-id for sending authenticated packet";
                reference
                '{
                    "attribute-getter" : {
                        "attribute" : "preferred"
                    }
                 }';
            }
            uses authentication-key;
        }
    }

    uses authentication-top;
}
