submodule rtbrick-subscriber-acl {
    yang-version 1.1;

    belongs-to rtbrick-config {
        prefix config;
    }

    import ietf-inet-types {
        prefix inet;
    }

    import rtbrick-types {
        prefix "rtb-types";
    }

    organization
      "Rtbrick";

    contact
      "Author : Vyshakh Krishnan (vyshakh@rtbrick.com)";

    description
      "This module describes the YANG model for the subscriber access control list (ACL) configuration.";

    revision 2023-05-11 {
        description
        "Configuration hierarchy for subscriber access control list";

        reference "None";
    }

    grouping subscriber-acl-match-l3v4 {
        description
            "Configure subscriber acl l3v4 match parameters.";
        container match {
            description
                "Configuration parameters relating subscriber acl l3v4 match.";
            reference
            '{
                "table-getter": {
                    "library" : "libprotoinfrayang.so",
                    "symbol"  : "proto_infra_yang_get_subscriber_acl_l3v4_cfg_tbl_templ",
                    "type"    : "global_subscriber_acl_l3v4_config_table",
                    "inherit-attribute" : [ "rule_name", "ordinal" ]
                }
            }';
            leaf destination-ipv4-prefix {
                type inet:ipv4-prefix;
                description
                    "Configure acl l3 ipv4 destination prefix match.";
                reference
                '{
                    "attribute-getter" : {
                        "attribute" : "match_destination_ipv4_prefix"
                    }
                }';
            }
            leaf source-ipv4-prefix {
                type inet:ipv4-prefix;
                description
                    "Configure acl l3 ipv4 source prefix match.";
                reference
                '{
                    "attribute-getter" : {
                        "attribute" : "match_source_ipv4_prefix"
                    }
                }';
            }
            leaf source-ipv4-prefix-list {
                type rtb-types:string64;
                description
                    "Configuring acl source ipv4 prefix list name";
                    reference
                    '{
                        "attribute-getter" : {
                            "attribute" : "match_source_ipv4_prefix_list",
                            "expansion-getter" : {
                                "package":"protoinfra",
                                "method" :"proto_infra_prefix_list_v4_name_expander"
                            }
                        }
                    }';
            }
            leaf destination-ipv4-prefix-list {
                type rtb-types:string64;
                description
                    "Configuring acl destination ipv4 prefix list name";
                    reference
                    '{
                        "attribute-getter" : {
                            "attribute" : "match_destination_ipv4_prefix_list",
                            "expansion-getter" : {
                                "package":"protoinfra",
                                "method" :"proto_infra_prefix_list_v4_name_expander"
                            }
                        }
                    }';
            }
            leaf destination-ipv4-subscriber-prefix {
                type rtb-types:boolean-true;
                description
                    "Configure acl to match for subscriber IPv4 address as destination.";
                reference
                '{
                    "attribute-getter" : {
                        "attribute" : "match_destination_ipv4_subscriber_prefix"
                    }
                }';
            }
            leaf source-ipv4-subscriber-prefix {
                type rtb-types:boolean-true;
                description
                    "Configure acl to match for subscriber IPv4 address as source.";
                reference
                '{
                    "attribute-getter" : {
                        "attribute" : "match_source_ipv4_subscriber_prefix"
                    }
                }';
            }
            leaf subscriber-ifl {
                type rtb-types:boolean-true;
                description
                    "Configure acl to match for all IPv4 traffic ingressing the subscriber ifl";
                reference
                '{
                    "attribute-getter" : {
                        "attribute" : "match_subscriber_ifl"
                    }
                }';
            }
            leaf destination-l4-port {
                type uint16;
                description
                    "Configure acl l4 destination port match.";
                reference
                '{
                    "attribute-getter" : {
                        "attribute" : "match_destination_l4_port"
                    }
                }';
            }
            leaf ip-protocol {
                type rtb-types:type-ipproto;
                description
                    "Configure acl ip protocol value match.";
                reference
                '{
                    "attribute-getter" : {
                        "attribute" : "match_ip_protocol"
                    }
                }';
            }
            leaf source-l4-port {
                type uint16;
                description
                    "Configure acl l4 source port match.";
                reference
                '{
                    "attribute-getter" : {
                        "attribute" : "match_source_l4_port"
                    }
                }';
            }
        }

    }

    grouping subscriber-acl-match-l3v6 {
        description
            "Configure acl l3v6 match parameters.";
        container match {
            description
                "Configuration parameters relating acl l3v6 match";
            reference
            '{
                "table-getter": {
                    "library" : "libprotoinfrayang.so",
                    "symbol"  : "proto_infra_yang_get_subscriber_acl_l3v6_cfg_tbl_templ",
                    "type"    : "global_subscriber_acl_l3v6_config_table",
                    "inherit-attribute" : [ "rule_name", "ordinal" ]
                }
            }';
            leaf destination-ipv6-prefix {
                type string;
                description
                    "Configure acl l3 ipv6 destination prefix match.";
                reference
                '{
                    "attribute-getter" : {
                        "attribute" : "match_destination_ipv6_prefix"
                    }
                }';
            }
            leaf source-ipv6-prefix {
                type inet:ipv6-prefix;
                description
                    "Configure acl l3 ipv6 source prefix match.";
                reference
                '{
                    "attribute-getter" : {
                        "attribute" : "match_source_ipv6_prefix"
                    }
                }';
            }
            leaf destination-ipv6-subscriber-prefix {
                type rtb-types:boolean-true;
                description
                    "Configure acl to match for subscriber IPv6 prefix as destination.";
                reference
                '{
                    "attribute-getter" : {
                        "attribute" : "match_destination_ipv6_subscriber_prefix"
                    }
                }';
            }
            leaf source-ipv6-subscriber-prefix {
                type rtb-types:boolean-true;
                description
                    "Configure acl to match for subscriber IPv6 prefix as source.";
                reference
                '{
                    "attribute-getter" : {
                        "attribute" : "match_source_ipv6_subscriber_prefix"
                    }
                }';
            }
            leaf destination-ipv6-delegated-subscriber-prefix {
                type rtb-types:boolean-true;
                description
                    "Configure acl to match for delegated subscriber IPv6 prefix as destination.";
                reference
                '{
                    "attribute-getter" : {
                        "attribute" : "match_destination_ipv6_delegated_subscriber_prefix"
                    }
                }';
            }
            leaf source-ipv6-delegated-subscriber-prefix {
                type rtb-types:boolean-true;
                description
                    "Configure acl to match for delegated subscriber IPv6 prefix as source.";
                reference
                '{
                    "attribute-getter" : {
                        "attribute" : "match_source_ipv6_delegated_subscriber_prefix"
                    }
                }';
            }
            leaf subscriber-ifl {
                type rtb-types:boolean-true;
                description
                    "Configure acl to match for all IPv6 traffic ingressing the subscriber ifl";
                reference
                '{
                    "attribute-getter" : {
                        "attribute" : "match_subscriber_ifl"
                    }
                }';
            }
            leaf source-ipv6-prefix-list {
                type rtb-types:string64;
                description
                    "Configuring acl source ipv6 prefix list name";
                    reference
                    '{
                        "attribute-getter" : {
                            "attribute" : "match_source_ipv6_prefix_list",
                            "expansion-getter" : {
                                "package":"protoinfra",
                                "method" :"proto_infra_prefix_list_v6_name_expander"
                            }
                        }
                    }';
            }

            leaf destination-ipv6-prefix-list {
                type rtb-types:string64;
                description
                    "Configuring acl destination ipv6 prefix list name";
                    reference
                    '{
                        "attribute-getter" : {
                            "attribute" : "match_destination_ipv6_prefix_list",
                            "expansion-getter" : {
                                "package":"protoinfra",
                                "method" :"proto_infra_prefix_list_v6_name_expander"
                            }
                        }
                    }';
            }
            leaf destination-l4-port {
                type uint16;
                description
                    "Configure acl l4 destination port match.";
                reference
                '{
                    "attribute-getter" : {
                        "attribute" : "match_destination_l4_port"
                    }
                }';
            }
            leaf ip-protocol {
                type rtb-types:type-ipproto;
                description
                    "Configure acl ip protocol value match.";
                reference
                '{
                    "attribute-getter" : {
                        "attribute" : "match_ip_protocol"
                    }
                }';
            }
            leaf source-l4-port {
                type uint16;
                description
                    "Configure acl l4 source port match.";
                reference
                '{
                    "attribute-getter" : {
                        "attribute" : "match_source_l4_port"
                    }
                }';
            }
        }
    }

    grouping subscriber-acl-action-l3v4 {
        description
            "Configure subscriber l3v4 acl action.";
        container action {
            description
                "Container for l3v4 acl action parameters.";
            reference
            '{
                "table-getter": {
                    "library" : "libprotoinfrayang.so",
                    "symbol"  : "proto_infra_yang_get_subscriber_acl_l3v4_cfg_tbl_templ",
                    "type"    : "global_subscriber_acl_l3v4_config_table",
                    "inherit-attribute" : [ "rule_name", "ordinal" ]
                }
            }';
            leaf drop {
                type rtb-types:boolean-true;
                description
                    "Configure action, drop packets.";
                reference
                '{
                    "attribute-getter" : {
                        "attribute" : "action_drop"
                    }
                }';
            }
            leaf permit {
                type rtb-types:boolean-true;
                description
                    "Configure action, permit packets.";
                reference
                '{
                    "attribute-getter" : {
                        "attribute" : "action_permit"
                    }
                }';
            }
            leaf http-redirect {
                type rtb-types:boolean-true;
                description
                    "Configure http redirect";
                reference
                '{
                    "attribute-getter" : {
                        "attribute" : "action_http_redirect"
                    }
                }';
            }
        } // container action
    }

    grouping subscriber-acl-action-l3v6 {
        description
            "Configure subscriber l3v6 acl action.";
        container action {
            description
                "Container for l3v6 acl action parameters.";
            reference
            '{
                "table-getter": {
                    "library" : "libprotoinfrayang.so",
                    "symbol"  : "proto_infra_yang_get_subscriber_acl_l3v6_cfg_tbl_templ",
                    "type"    : "global_subscriber_acl_l3v6_config_table",
                    "inherit-attribute" : [ "rule_name", "ordinal" ]
                }
            }';
            leaf drop {
                type rtb-types:boolean-true;
                description
                    "Configure action, drop packets.";
                reference
                '{
                    "attribute-getter" : {
                        "attribute" : "action_drop"
                    }
                }';
            }
            leaf permit {
                type rtb-types:boolean-true;
                description
                    "Configure action, permit packets.";
                reference
                '{
                    "attribute-getter" : {
                        "attribute" : "action_permit"
                    }
                }';
            }
            leaf http-redirect {
                type rtb-types:boolean-true;
                description
                    "Configure http redirect";
                reference
                '{
                    "attribute-getter" : {
                        "attribute" : "action_http_redirect"
                    }
                }';
            }
        } // container action
    }

    grouping subscriber-acl-top {
        description
            "Top-level grouping containing a list of subscriber acl config.";
        container subscriber-acl {
            description
                "container for list of subscriber acl config.";
            container l3v4 {
                description
                    "container for l3v4 subscriber acl config.";
                list rule {
                    key "rule-name";
                    description
                        "Configuration parameters relating subscriber acl rule.";
                    reference
                    '{
                        "table-getter": {
                            "library" : "libprotoinfrayang.so",
                            "symbol"  : "proto_infra_yang_get_subscriber_acl_l3v4_mode_cfg_tbl_templ",
                            "type"    : "global_subscriber_acl_l3v4_mode_config_table"
                        }
                    }';
                    leaf rule-name {
                        type string;
                        description
                            "Configure subscriber acl rule name.";
                        reference
                        '{
                            "attribute-getter" : {
                                "attribute" : "rule_name"
                            }
                        }';
                    }
                    list ordinal {
                        key "ordinal-value";
                        description
                            "Configuration parameters relating subscriber acl ordinal.";
                        reference
                        '{
                            "table-getter": {
                                "library" : "libprotoinfrayang.so",
                                "symbol"  : "proto_infra_yang_get_subscriber_acl_l3v4_cfg_tbl_templ",
                                "type"    : "global_subscriber_acl_l3v4_config_table",
                                "inherit-attribute" : [ "rule_name" ]
                            }
                        }';
                        leaf ordinal-value {
                            type uint32 {
                                range "0 .. 200000";
                            }
                            description
                                "Configure ordinal value";
                            reference
                            '{
                                "attribute-getter" : {
                                    "attribute" : "ordinal"
                                }
                            }';
                        }
                        uses subscriber-acl-match-l3v4;
                        uses subscriber-acl-action-l3v4;

                        leaf priority {
                            type uint16 {
                                range "100 .. 20000";
                            }
                            description
                                "Configure subscriber acl priority value.";
                            reference
                            '{
                                "attribute-getter" : {
                                    "attribute" : "priority"
                                }
                            }';
                        }
                    }
                }
            } // container l3v4
            container l3v6 {
                description
                    "container for l3v6 subscriber acl config.";
                list rule {
                    key "rule-name";
                    description
                        "Configuration parameters relating acl rule";
                    reference
                    '{
                        "table-getter": {
                            "library" : "libprotoinfrayang.so",
                            "symbol"  : "proto_infra_yang_get_subscriber_acl_l3v6_mode_cfg_tbl_templ",
                            "type"    : "global_subscriber_acl_l3v6_mode_config_table"
                        }
                    }';
                    leaf rule-name {
                        type string;
                        description
                            "Configure acl rule name.";
                        reference
                        '{
                            "attribute-getter" : {
                                "attribute" : "rule_name"
                            }
                        }';
                    }
                    list ordinal {
                        key "ordinal-value";
                        description
                            "Configuration parameters relating acl ordinal.";
                        reference
                        '{
                            "table-getter": {
                                "library" : "libprotoinfrayang.so",
                                "symbol"  : "proto_infra_yang_get_subscriber_acl_l3v6_cfg_tbl_templ",
                                "type"    : "global_subscriber_acl_l3v6_config_table",
                                "inherit-attribute" : [ "rule_name"]
                            }
                        }';
                        leaf ordinal-value {
                            type uint32 {
                                range "0 .. 200000";
                            }
                            description
                                "Configure ordinal value.";
                            reference
                            '{
                                "attribute-getter" : {
                                    "attribute" : "ordinal"
                                }
                            }';
                        }
                        uses subscriber-acl-match-l3v6;
                        uses subscriber-acl-action-l3v6;
                        leaf priority {
                            type uint16 {
                                range "100 .. 20000";
                            }
                            description
                                "Configure acl priority value.";
                            reference
                            '{
                                "attribute-getter" : {
                                    "attribute" : "priority"
                                }
                            }';
                        }
                    }
                }
            } // container l3v6
        } // container subscriber-acl
    }// grouping subscriber-acl-top
}
