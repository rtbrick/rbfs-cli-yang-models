submodule rtbrick-access-user-profile {

    yang-version 1.1;

    belongs-to rtbrick-config {
        prefix config;
    }

    import rtbrick-types {
        prefix "rtb-types";
    }

    organization
      "RtBrick";
    contact
      "Authors: Vyshakh Krishnan (vyshakh@rtbrick.com)";
    description
      "This sub-module contains yang structure for
       access user profile.";
    revision 2020-07-24 {
        description "First revision";
        reference "None";
    }

    typedef tunnel-type {
        type enumeration {
            enum PPPoE {
                value "0";
                description "PPPoE";
	        }
            enum L2TP {
                value "1";
                description "L2TP";
	        }
        }
        description "Tunnel type";
    }

    grouping access-user-profile {
        description "Global access user profile configuration";
        
        list user-profile {
            key "user-name";
            description "Global user profile configuration";
            reference
            '{
                "table-getter": {
                    "library" : "libcmdsubsMgmt.so",
                    "symbol"  : "subsMgmt_cfg_cmd_user_profile_tbl_get",
                    "type"    : "user_profile_config_table"
                }
            }';                                                      
            leaf user-name {
                type string {
                    length "1 .. 250";
                }
                description "Username";
                reference
                '{
                    "attribute-getter" : {
                        "attribute" : "user_name"
                    }
                }';
            }
            leaf password-plain-text {
                type string {
                    length "1..64";
                }
                description "Secret/password in plain text";
                reference
                '{
                    "attribute-getter" : {
                        "attribute" : "password",
                        "plain-text-password" : true,
			            "secret-text-leaf-name" : "password-encrypted-text"
                    }
                }';
            }
            leaf password-encrypted-text {
                type rtb-types:secret-string-type;
                description "Secret/password in encrypted text";
                reference
                '{
                    "attribute-getter" : {
                        "attribute" : "password"
                    }
               }';
            }
            leaf tunnel-type {
                type tunnel-type;
                description "Tunnel type";
                reference
                '{
                    "attribute-getter" : {
                        "attribute" : "tunnel_type"
                    }
                }';
            } 
            leaf l2tp-pool-name {
                type string {
                    length "1..64";
                }
                description "L2TP pool name";
                reference
                '{
                    "attribute-getter" : {
                        "attribute" : "l2tp_pool_name"
                    }
                }';
            }
        }
    }
}
