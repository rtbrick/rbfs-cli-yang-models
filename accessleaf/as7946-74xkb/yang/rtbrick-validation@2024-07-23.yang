submodule rtbrick-validation {
    yang-version 1.1;
    belongs-to rtbrick-config {
        prefix config;
    }

    import ietf-inet-types {
        prefix "inet";
    }

    import clixon-autocli{
        prefix autocli;
    }

    organization "RtBrick";

    revision "2024-07-23" {
      description
        "First revision of Validation configuration";
      reference
        "None";

    }

    grouping session-config {
        description "Session configuration";
        leaf authentication-id {
            type string{
                length "1..64";
            }
            description "Authentication ID";
            reference
            '{
                "attribute-getter" : {
                    "attribute" : "auth_id"
                }
            }';
        }
        leaf port-number {
            type uint16 {
                range "1..65535";
            }
            description "Port number used for cache connection";
            reference
            '{
                "attribute-getter" : {
                    "attribute" : "port"
                }
            }';
        }
        leaf preference {
            type uint16 {
                range "1..65535";
            }
            description "Cache preference";
            reference
            '{
                "attribute-getter" : {
                    "attribute" : "preference"
                }
            }';
        }
        leaf record-lifetime {
            type uint32 {
                range "1..3600";
            }
            autocli:hide;
            description "Lifetime of the record in cache";
            reference
            '{
                "attribute-getter" : {
                    "attribute" : "record_lifetime"
                }
            }';
        }
        leaf refresh-time {
            type uint32 {
                range "1..3600";
            }
            autocli:hide;
            description "Refresh time";
            reference
            '{
                "attribute-getter" : {
                    "attribute" : "refresh_time"
                }
            }';
        }
    }

    grouping validation-top {
        description "Validation data";
        container validation {
            description "Validation protocol configuration";
            reference
            '{
                "table-getter" : {
                    "table-name" : "global.validation.instance.config",
                    "type"       : "validation_instance_config_table", 
                    "inherit-attribute":["instance_name"]
                }
            }'; 
            container session {
                list ipv4 {
                    key "cache-address update-source";
                    description "IPv4 address";
                    reference
                    '{
                        "table-getter": {
                            "library": "libcmdvalidation.so",
                            "symbol": "validation_yang_cache_cfg_ipv4_table_tmpl_get",
                            "type" :  "validation_cache_config_ipv4_table"
                        }
                    }';
                    leaf cache-address {
                        type inet:ipv4-address-no-zone;
                        description "Cache IPv4 address to which TCP session has to be established";
                        reference
                        '{
                            "attribute-getter" : {
                                "attribute" : "cache_ipv4_address"
                            }
                        }';
                    }
                    leaf update-source {
                        type inet:ipv4-address-no-zone;
                        description "Source IPv4 address in the TCP session";
                        reference
                        '{
                            "attribute-getter" : {
                                "attribute" : "src_ipv4_address"
                            }
                        }';
                    }
                    uses session-config;
                }
                list ipv6 {
                    key "cache-address update-source";
                    description "IPv6 address";
                    reference
                    '{
                        "table-getter": {
                            "library": "libcmdvalidation.so",
                            "symbol": "validation_yang_cache_cfg_ipv6_table_tmpl_get",
                            "type" :  "validation_cache_config_ipv6_table"
                        }
                    }';
                    leaf cache-address {
                        type inet:ipv6-address-no-zone;
                        description "Cache IPv6 address to which TCP session has to be established";
                        reference
                        '{
                            "attribute-getter" : {
                                "attribute" : "cache_ipv6_address"
                            }
                        }';
                    }
                    leaf update-source {
                        type inet:ipv6-address-no-zone;
                        description "Source IPv6 address in the TCP session";
                        reference
                        '{
                            "attribute-getter" : {
                                "attribute" : "src_ipv6_address"
                            }
                        }';
                    }
                    uses session-config;
                }
            }
        }
    }
}
