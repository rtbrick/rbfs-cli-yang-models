submodule rtbrick-isis {
    yang-version 1.1;
    belongs-to rtbrick-config {
        prefix config;
    }

    organization
      "Rtbrick";
    contact
      "yang-support@rtbrick.com";

    description
        "This sub module contains the top level configurations of dummy isis configuration to help rtbrick roles
  	This must be dated before the latest package";

    revision 2020-01-01 {
        description
          "Dummy isis yang file";
        reference "None";
    }


    grouping isis-global-top  {
        description "Dummy global isis top level config";
    }

    grouping isis-top {
        description "Dummy isis top level config";

    }
}
